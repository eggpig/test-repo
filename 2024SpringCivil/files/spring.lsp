(command "line" '(9.18485099360515e-16 15.0 0.0) '(-2.6047226650039548 14.772116295183121 0.2777777777777778) "")
 (command "line" '(-2.6047226650039548 14.772116295183121 0.2777777777777778) '(-5.130302149885031 14.095389311788626 0.5555555555555556) "")
 (command "line" '(-5.130302149885031 14.095389311788626 0.5555555555555556) '(-7.4999999999999964 12.99038105676658 0.8333333333333333) "")
 (command "line" '(-7.4999999999999964 12.99038105676658 0.8333333333333333) '(-9.64181414529809 11.49066664678467 1.1111111111111112) "")
 (command "line" '(-9.64181414529809 11.49066664678467 1.1111111111111112) '(-11.490666646784668 9.641814145298092 1.3888888888888888) "")
 (command "line" '(-11.490666646784668 9.641814145298092 1.3888888888888888) '(-12.99038105676658 7.499999999999999 1.6666666666666665) "")
 (command "line" '(-12.99038105676658 7.499999999999999 1.6666666666666665) '(-14.095389311788624 5.130302149885033 1.9444444444444444) "")
 (command "line" '(-14.095389311788624 5.130302149885033 1.9444444444444444) '(-14.772116295183121 2.6047226650039605 2.2222222222222223) "")
 (command "line" '(-14.772116295183121 2.6047226650039605 2.2222222222222223) '(-15.0 1.83697019872103e-15 2.5) "")
 (command "line" '(-15.0 1.83697019872103e-15 2.5) '(-14.772116295183121 -2.604722665003957 2.7777777777777777) "")
 (command "line" '(-14.772116295183121 -2.604722665003957 2.7777777777777777) '(-14.095389311788626 -5.13030214988503 3.055555555555556) "")
 (command "line" '(-14.095389311788626 -5.13030214988503 3.055555555555556) '(-12.990381056766578 -7.500000000000002 3.333333333333333) "")
 (command "line" '(-12.990381056766578 -7.500000000000002 3.333333333333333) '(-11.49066664678467 -9.641814145298088 3.611111111111111) "")
 (command "line" '(-11.49066664678467 -9.641814145298088 3.611111111111111) '(-9.641814145298092 -11.490666646784668 3.888888888888889) "")
 (command "line" '(-9.641814145298092 -11.490666646784668 3.888888888888889) '(-7.500000000000007 -12.990381056766577 4.166666666666667) "")
 (command "line" '(-7.500000000000007 -12.990381056766577 4.166666666666667) '(-5.130302149885041 -14.095389311788622 4.444444444444445) "")
 (command "line" '(-5.130302149885041 -14.095389311788622 4.444444444444445) '(-2.6047226650039548 -14.772116295183121 4.722222222222222) "")
 (command "line" '(-2.6047226650039548 -14.772116295183121 4.722222222222222) '(-2.7554552980815444e-15 -15.0 5.0) "")
 (command "line" '(-2.7554552980815444e-15 -15.0 5.0) '(2.6047226650039494 -14.772116295183121 5.277777777777778) "")
 (command "line" '(2.6047226650039494 -14.772116295183121 5.277777777777778) '(5.1303021498850345 -14.095389311788624 5.555555555555555) "")
 (command "line" '(5.1303021498850345 -14.095389311788624 5.555555555555555) '(7.500000000000002 -12.990381056766578 5.833333333333334) "")
 (command "line" '(7.500000000000002 -12.990381056766578 5.833333333333334) '(9.641814145298088 -11.490666646784671 6.111111111111112) "")
 (command "line" '(9.641814145298088 -11.490666646784671 6.111111111111112) '(11.490666646784668 -9.641814145298094 6.388888888888888) "")
 (command "line" '(11.490666646784668 -9.641814145298094 6.388888888888888) '(12.990381056766577 -7.500000000000007 6.666666666666666) "")
 (command "line" '(12.990381056766577 -7.500000000000007 6.666666666666666) '(14.09538931178862 -5.130302149885042 6.944444444444445) "")
 (command "line" '(14.09538931178862 -5.130302149885042 6.944444444444445) '(14.772116295183121 -2.6047226650039557 7.222222222222222) "")
 (command "line" '(14.772116295183121 -2.6047226650039557 7.222222222222222) '(15.0 -3.67394039744206e-15 7.5) "")
 (command "line" '(15.0 -3.67394039744206e-15 7.5) '(14.772116295183121 2.6047226650039486 7.777777777777778) "")
 (command "line" '(14.772116295183121 2.6047226650039486 7.777777777777778) '(14.095389311788624 5.130302149885034 8.055555555555555) "")
 (command "line" '(14.095389311788624 5.130302149885034 8.055555555555555) '(12.990381056766585 7.499999999999989 8.333333333333334) "")
 (command "line" '(12.990381056766585 7.499999999999989 8.333333333333334) '(11.490666646784671 9.641814145298088 8.61111111111111) "")
 (command "line" '(11.490666646784671 9.641814145298088 8.61111111111111) '(9.641814145298094 11.490666646784668 8.88888888888889) "")
 (command "line" '(9.641814145298094 11.490666646784668 8.88888888888889) '(7.499999999999996 12.990381056766582 9.166666666666666) "")
 (command "line" '(7.499999999999996 12.990381056766582 9.166666666666666) '(5.1303021498850425 14.09538931178862 9.444444444444445) "")
 (command "line" '(5.1303021498850425 14.09538931178862 9.444444444444445) '(2.6047226650039565 14.772116295183121 9.722222222222221) "")
 (command "line" '(2.6047226650039565 14.772116295183121 9.722222222222221) '(4.592425496802574e-15 15.0 10.0) "")
 (command "line" '(4.592425496802574e-15 15.0 10.0) '(-2.6047226650039477 14.772116295183121 10.277777777777777) "")
 (command "line" '(-2.6047226650039477 14.772116295183121 10.277777777777777) '(-5.13030214988502 14.09538931178863 10.555555555555555) "")
 (command "line" '(-5.13030214988502 14.09538931178863 10.555555555555555) '(-7.4999999999999885 12.990381056766587 10.833333333333332) "")
 (command "line" '(-7.4999999999999885 12.990381056766587 10.833333333333332) '(-9.641814145298097 11.490666646784664 11.11111111111111) "")
 (command "line" '(-9.641814145298097 11.490666646784664 11.11111111111111) '(-11.490666646784659 9.641814145298106 11.38888888888889) "")
 (command "line" '(-11.490666646784659 9.641814145298106 11.38888888888889) '(-12.990381056766582 7.4999999999999964 11.666666666666668) "")
 (command "line" '(-12.990381056766582 7.4999999999999964 11.666666666666668) '(-14.095389311788626 5.130302149885031 11.944444444444445) "")
 (command "line" '(-14.095389311788626 5.130302149885031 11.944444444444445) '(-14.772116295183121 2.6047226650039574 12.222222222222223) "")
 (command "line" '(-14.772116295183121 2.6047226650039574 12.222222222222223) '(-15.0 5.510910596163089e-15 12.5) "")
 (command "line" '(-15.0 5.510910596163089e-15 12.5) '(-14.772116295183121 -2.604722665003947 12.777777777777777) "")
 (command "line" '(-14.772116295183121 -2.604722665003947 12.777777777777777) '(-14.09538931178863 -5.13030214988502 13.055555555555555) "")
 (command "line" '(-14.09538931178863 -5.13030214988502 13.055555555555555) '(-12.990381056766587 -7.499999999999988 13.333333333333332) "")
 (command "line" '(-12.990381056766587 -7.499999999999988 13.333333333333332) '(-11.490666646784666 -9.641814145298097 13.61111111111111) "")
 (command "line" '(-11.490666646784666 -9.641814145298097 13.61111111111111) '(-9.641814145298106 -11.490666646784657 13.88888888888889) "")
 (command "line" '(-9.641814145298106 -11.490666646784657 13.88888888888889) '(-7.499999999999997 -12.99038105676658 14.166666666666668) "")
 (command "line" '(-7.499999999999997 -12.99038105676658 14.166666666666668) '(-5.130302149885032 -14.095389311788626 14.444444444444445) "")
 (command "line" '(-5.130302149885032 -14.095389311788626 14.444444444444445) '(-2.6047226650039588 -14.772116295183121 14.722222222222223) "")
 (command "line" '(-2.6047226650039588 -14.772116295183121 14.722222222222223) '(-6.429395695523604e-15 -15.0 15.0) "")
 (command "line" '(-6.429395695523604e-15 -15.0 15.0) '(2.604722665003946 -14.772116295183121 15.277777777777777) "")
 (command "line" '(2.604722665003946 -14.772116295183121 15.277777777777777) '(5.130302149885019 -14.09538931178863 15.555555555555555) "")
 (command "line" '(5.130302149885019 -14.09538931178863 15.555555555555555) '(7.499999999999987 -12.990381056766587 15.833333333333332) "")
 (command "line" '(7.499999999999987 -12.990381056766587 15.833333333333332) '(9.641814145298095 -11.490666646784666 16.11111111111111) "")
 (command "line" '(9.641814145298095 -11.490666646784666 16.11111111111111) '(11.490666646784657 -9.641814145298108 16.38888888888889) "")
 (command "line" '(11.490666646784657 -9.641814145298108 16.38888888888889) '(12.99038105676658 -7.499999999999998 16.666666666666668) "")
 (command "line" '(12.99038105676658 -7.499999999999998 16.666666666666668) '(14.095389311788624 -5.130302149885033 16.944444444444443) "")
 (command "line" '(14.095389311788624 -5.130302149885033 16.944444444444443) '(14.772116295183121 -2.6047226650039597 17.22222222222222) "")
 (command "line" '(14.772116295183121 -2.6047226650039597 17.22222222222222) '(15.0 -7.34788079488412e-15 17.5) "")
 (command "line" '(15.0 -7.34788079488412e-15 17.5) '(14.772116295183121 2.604722665003945 17.77777777777778) "")
 (command "line" '(14.772116295183121 2.604722665003945 17.77777777777778) '(14.09538931178863 5.1303021498850185 18.055555555555557) "")
 (command "line" '(14.09538931178863 5.1303021498850185 18.055555555555557) '(12.990381056766575 7.500000000000008 18.333333333333332) "")
 (command "line" '(12.990381056766575 7.500000000000008 18.333333333333332) '(11.490666646784666 9.641814145298095 18.61111111111111) "")
 (command "line" '(11.490666646784666 9.641814145298095 18.61111111111111) '(9.641814145298108 11.490666646784655 18.88888888888889) "")
 (command "line" '(9.641814145298108 11.490666646784655 18.88888888888889) '(7.500000000000021 12.990381056766568 19.166666666666668) "")
 (command "line" '(7.500000000000021 12.990381056766568 19.166666666666668) '(5.130302149885033 14.095389311788624 19.444444444444443) "")
 (command "line" '(5.130302149885033 14.095389311788624 19.444444444444443) '(2.6047226650039605 14.772116295183121 19.72222222222222) "")
 (command "line" '(2.6047226650039605 14.772116295183121 19.72222222222222) '(8.266365894244635e-15 15.0 20.0) "")
 (command "line" '(8.266365894244635e-15 15.0 20.0) '(-2.604722665003944 14.772116295183123 20.27777777777778) "")
 (command "line" '(-2.604722665003944 14.772116295183123 20.27777777777778) '(-5.130302149885018 14.095389311788631 20.555555555555554) "")
 (command "line" '(-5.130302149885018 14.095389311788631 20.555555555555554) '(-7.500000000000008 12.990381056766577 20.833333333333336) "")
 (command "line" '(-7.500000000000008 12.990381056766577 20.833333333333336) '(-9.641814145298095 11.490666646784668 21.11111111111111) "")
 (command "line" '(-9.641814145298095 11.490666646784668 21.11111111111111) '(-11.490666646784655 9.64181414529811 21.38888888888889) "")
 (command "line" '(-11.490666646784655 9.64181414529811 21.38888888888889) '(-12.990381056766566 7.500000000000023 21.666666666666664) "")
 (command "line" '(-12.990381056766566 7.500000000000023 21.666666666666664) '(-14.095389311788624 5.130302149885034 21.944444444444446) "")
 (command "line" '(-14.095389311788624 5.130302149885034 21.944444444444446) '(-14.772116295183121 2.604722665003961 22.22222222222222) "")
 (command "line" '(-14.772116295183121 2.604722665003961 22.22222222222222) '(-15.0 9.184850993605149e-15 22.5) "")
 (command "line" '(-15.0 9.184850993605149e-15 22.5) '(-14.772116295183123 -2.6047226650039432 22.77777777777778) "")
 (command "line" '(-14.772116295183123 -2.6047226650039432 22.77777777777778) '(-14.095389311788631 -5.130302149885017 23.055555555555554) "")
 (command "line" '(-14.095389311788631 -5.130302149885017 23.055555555555554) '(-12.990381056766589 -7.499999999999984 23.333333333333336) "")
 (command "line" '(-12.990381056766589 -7.499999999999984 23.333333333333336) '(-11.490666646784684 -9.641814145298074 23.61111111111111) "")
 (command "line" '(-11.490666646784684 -9.641814145298074 23.61111111111111) '(-9.64181414529811 -11.490666646784655 23.88888888888889) "")
 (command "line" '(-9.64181414529811 -11.490666646784655 23.88888888888889) '(-7.500000000000023 -12.990381056766566 24.166666666666664) "")
 (command "line" '(-7.500000000000023 -12.990381056766566 24.166666666666664) '(-5.13030214988501 -14.095389311788633 24.444444444444446) "")
 (command "line" '(-5.13030214988501 -14.095389311788633 24.444444444444446) '(-2.6047226650039357 -14.772116295183123 24.72222222222222) "")
 (command "line" '(-2.6047226650039357 -14.772116295183123 24.72222222222222) '(-3.674868868396942e-14 -15.0 25.0) "")
 (command "line" '(-3.674868868396942e-14 -15.0 25.0) '(2.6047226650039157 -14.772116295183126 25.27777777777778) "")
 (command "line" '(2.6047226650039157 -14.772116295183126 25.27777777777778) '(5.130302149884991 -14.09538931178864 25.555555555555554) "")
 (command "line" '(5.130302149884991 -14.09538931178864 25.555555555555554) '(7.500000000000007 -12.990381056766577 25.833333333333336) "")
 (command "line" '(7.500000000000007 -12.990381056766577 25.833333333333336) '(9.641814145298094 -11.490666646784668 26.11111111111111) "")
 (command "line" '(9.641814145298094 -11.490666646784668 26.11111111111111) '(11.490666646784671 -9.641814145298088 26.38888888888889) "")
 (command "line" '(11.490666646784671 -9.641814145298088 26.38888888888889) '(12.990381056766578 -7.500000000000002 26.666666666666664) "")
 (command "line" '(12.990381056766578 -7.500000000000002 26.666666666666664) '(14.095389311788624 -5.130302149885035 26.944444444444446) "")
 (command "line" '(14.095389311788624 -5.130302149885035 26.944444444444446) '(14.772116295183121 -2.6047226650039628 27.22222222222222) "")
 (command "line" '(14.772116295183121 -2.6047226650039628 27.22222222222222) '(15.0 -1.1021821192326178e-14 27.5) "")
 (command "line" '(15.0 -1.1021821192326178e-14 27.5) '(14.772116295183123 2.6047226650039415 27.77777777777778) "")
 (command "line" '(14.772116295183123 2.6047226650039415 27.77777777777778) '(14.095389311788631 5.130302149885015 28.055555555555554) "")
 (command "line" '(14.095389311788631 5.130302149885015 28.055555555555554) '(12.990381056766589 7.499999999999982 28.333333333333336) "")
 (command "line" '(12.990381056766589 7.499999999999982 28.333333333333336) '(11.490666646784685 9.641814145298072 28.61111111111111) "")
 (command "line" '(11.490666646784685 9.641814145298072 28.61111111111111) '(9.64181414529811 11.490666646784653 28.88888888888889) "")
 (command "line" '(9.64181414529811 11.490666646784653 28.88888888888889) '(7.500000000000025 12.990381056766566 29.166666666666664) "")
 (command "line" '(7.500000000000025 12.990381056766566 29.166666666666664) '(5.130302149885011 14.095389311788633 29.444444444444446) "")
 (command "line" '(5.130302149885011 14.095389311788633 29.444444444444446) '(2.604722665003938 14.772116295183123 29.72222222222222) "")
 (command "line" '(2.604722665003938 14.772116295183123 29.72222222222222) '(-1.470504629931706e-14 15.0 30.0) "")
 (command "line" '(-1.470504629931706e-14 15.0 30.0) '(-2.6047226650039144 14.772116295183128 30.27777777777778) "")
 (command "line" '(-2.6047226650039144 14.772116295183128 30.27777777777778) '(-5.130302149884989 14.095389311788642 30.555555555555554) "")
 (command "line" '(-5.130302149884989 14.095389311788642 30.555555555555554) '(-7.500000000000005 12.990381056766577 30.833333333333336) "")
 (command "line" '(-7.500000000000005 12.990381056766577 30.833333333333336) '(-9.641814145298092 11.490666646784668 31.11111111111111) "")
 (command "line" '(-9.641814145298092 11.490666646784668 31.11111111111111) '(-11.49066664678467 9.64181414529809 31.38888888888889) "")
 (command "line" '(-11.49066664678467 9.64181414529809 31.38888888888889) '(-12.990381056766577 7.5000000000000036 31.666666666666664) "")
 (command "line" '(-12.990381056766577 7.5000000000000036 31.666666666666664) '(-14.095389311788622 5.130302149885037 31.944444444444446) "")
 (command "line" '(-14.095389311788622 5.130302149885037 31.944444444444446) '(-14.77211629518312 2.604722665003965 32.22222222222222) "")
 (command "line" '(-14.77211629518312 2.604722665003965 32.22222222222222) '(-15.0 1.2858791391047208e-14 32.5) "")
 (command "line" '(-15.0 1.2858791391047208e-14 32.5) '(-14.772116295183123 -2.6047226650039397 32.77777777777778) "")
 (command "line" '(-14.772116295183123 -2.6047226650039397 32.77777777777778) '(-14.095389311788631 -5.130302149885013 33.05555555555556) "")
 (command "line" '(-14.095389311788631 -5.130302149885013 33.05555555555556) '(-12.99038105676659 -7.4999999999999805 33.333333333333336) "")
 (command "line" '(-12.99038105676659 -7.4999999999999805 33.333333333333336) '(-11.490666646784687 -9.64181414529807 33.611111111111114) "")
 (command "line" '(-11.490666646784687 -9.64181414529807 33.611111111111114) '(-9.641814145298111 -11.490666646784652 33.888888888888886) "")
 (command "line" '(-9.641814145298111 -11.490666646784652 33.888888888888886) '(-7.500000000000027 -12.990381056766564 34.166666666666664) "")
 (command "line" '(-7.500000000000027 -12.990381056766564 34.166666666666664) '(-5.130302149885013 -14.095389311788631 34.44444444444444) "")
 (command "line" '(-5.130302149885013 -14.095389311788631 34.44444444444444) '(-2.6047226650039397 -14.772116295183123 34.72222222222222) "")
 (command "line" '(-2.6047226650039397 -14.772116295183123 34.72222222222222) '(-4.042262908141148e-14 -15.0 35.0) "")
 (command "line" '(-4.042262908141148e-14 -15.0 35.0) '(2.6047226650039126 -14.772116295183128 35.27777777777778) "")
 (command "line" '(2.6047226650039126 -14.772116295183128 35.27777777777778) '(5.1303021498849875 -14.095389311788642 35.55555555555556) "")
 (command "line" '(5.1303021498849875 -14.095389311788642 35.55555555555556) '(7.5000000000000036 -12.990381056766577 35.833333333333336) "")
 (command "line" '(7.5000000000000036 -12.990381056766577 35.833333333333336) '(9.64181414529809 -11.49066664678467 36.111111111111114) "")
 (command "line" '(9.64181414529809 -11.49066664678467 36.111111111111114) '(11.490666646784668 -9.641814145298092 36.388888888888886) "")
 (command "line" '(11.490666646784668 -9.641814145298092 36.388888888888886) '(12.990381056766577 -7.500000000000005 36.666666666666664) "")
 (command "line" '(12.990381056766577 -7.500000000000005 36.666666666666664) '(14.095389311788622 -5.130302149885039 36.94444444444444) "")
 (command "line" '(14.095389311788622 -5.130302149885039 36.94444444444444) '(14.77211629518312 -2.6047226650039668 37.22222222222222) "")
 (command "line" '(14.77211629518312 -2.6047226650039668 37.22222222222222) '(15.0 -1.469576158976824e-14 37.5) "")
 (command "line" '(15.0 -1.469576158976824e-14 37.5) '(14.772116295183123 2.604722665003938 37.77777777777778) "")
 (command "line" '(14.772116295183123 2.604722665003938 37.77777777777778) '(14.095389311788633 5.130302149885011 38.05555555555556) "")
 (command "line" '(14.095389311788633 5.130302149885011 38.05555555555556) '(12.990381056766592 7.49999999999998 38.333333333333336) "")
 (command "line" '(12.990381056766592 7.49999999999998 38.333333333333336) '(11.490666646784689 9.641814145298069 38.611111111111114) "")
 (command "line" '(11.490666646784689 9.641814145298069 38.611111111111114) '(9.641814145298072 11.490666646784685 38.888888888888886) "")
 (command "line" '(9.641814145298072 11.490666646784685 38.888888888888886) '(7.499999999999982 12.990381056766589 39.166666666666664) "")
 (command "line" '(7.499999999999982 12.990381056766589 39.166666666666664) '(5.130302149885015 14.095389311788631 39.44444444444444) "")
 (command "line" '(5.130302149885015 14.095389311788631 39.44444444444444) '(2.6047226650039415 14.772116295183123 39.72222222222222) "")
 (command "line" '(2.6047226650039415 14.772116295183123 39.72222222222222) '(-1.1031105901875003e-14 15.0 40.0) "")
 (command "line" '(-1.1031105901875003e-14 15.0 40.0) '(-2.6047226650039104 14.772116295183128 40.27777777777778) "")
 (command "line" '(-2.6047226650039104 14.772116295183128 40.27777777777778) '(-5.130302149884986 14.095389311788644 40.55555555555556) "")
 (command "line" '(-5.130302149884986 14.095389311788644 40.55555555555556) '(-7.499999999999955 12.990381056766605 40.83333333333333) "")
 (command "line" '(-7.499999999999955 12.990381056766605 40.83333333333333) '(-9.64181414529805 11.490666646784705 41.11111111111111) "")
 (command "line" '(-9.64181414529805 11.490666646784705 41.11111111111111) '(-11.490666646784668 9.641814145298094 41.38888888888889) "")
 (command "line" '(-11.490666646784668 9.641814145298094 41.38888888888889) '(-12.990381056766577 7.500000000000007 41.66666666666667) "")
 (command "line" '(-12.990381056766577 7.500000000000007 41.66666666666667) '(-14.09538931178862 5.130302149885041 41.94444444444444) "")
 (command "line" '(-14.09538931178862 5.130302149885041 41.94444444444444) '(-14.77211629518312 2.604722665003968 42.22222222222222) "")
 (command "line" '(-14.77211629518312 2.604722665003968 42.22222222222222) '(-15.0 1.653273178848927e-14 42.5) "")
 (command "line" '(-15.0 1.653273178848927e-14 42.5) '(-14.772116295183123 -2.6047226650039357 42.77777777777778) "")
 (command "line" '(-14.772116295183123 -2.6047226650039357 42.77777777777778) '(-14.095389311788633 -5.13030214988501 43.05555555555556) "")
 (command "line" '(-14.095389311788633 -5.13030214988501 43.05555555555556) '(-12.990381056766592 -7.499999999999978 43.33333333333333) "")
 (command "line" '(-12.990381056766592 -7.499999999999978 43.33333333333333) '(-11.490666646784689 -9.641814145298067 43.61111111111111) "")
 (command "line" '(-11.490666646784689 -9.641814145298067 43.61111111111111) '(-9.641814145298074 -11.490666646784684 43.88888888888889) "")
 (command "line" '(-9.641814145298074 -11.490666646784684 43.88888888888889) '(-7.499999999999984 -12.990381056766589 44.16666666666667) "")
 (command "line" '(-7.499999999999984 -12.990381056766589 44.16666666666667) '(-5.130302149885017 -14.095389311788631 44.44444444444444) "")
 (command "line" '(-5.130302149885017 -14.095389311788631 44.44444444444444) '(-2.6047226650039432 -14.772116295183123 44.72222222222222) "")
 (command "line" '(-2.6047226650039432 -14.772116295183123 44.72222222222222) '(-4.409656947885354e-14 -15.0 45.0) "")
 (command "line" '(-4.409656947885354e-14 -15.0 45.0) '(2.6047226650039086 -14.772116295183128 45.27777777777778) "")
 (command "line" '(2.6047226650039086 -14.772116295183128 45.27777777777778) '(5.130302149884984 -14.095389311788644 45.55555555555556) "")
 (command "line" '(5.130302149884984 -14.095389311788644 45.55555555555556) '(7.499999999999954 -12.990381056766605 45.83333333333333) "")
 (command "line" '(7.499999999999954 -12.990381056766605 45.83333333333333) '(9.641814145298047 -11.490666646784707 46.11111111111111) "")
 (command "line" '(9.641814145298047 -11.490666646784707 46.11111111111111) '(11.490666646784668 -9.641814145298095 46.38888888888889) "")
 (command "line" '(11.490666646784668 -9.641814145298095 46.38888888888889) '(12.990381056766577 -7.500000000000008 46.66666666666667) "")
 (command "line" '(12.990381056766577 -7.500000000000008 46.66666666666667) '(14.09538931178862 -5.1303021498850425 46.94444444444444) "")
 (command "line" '(14.09538931178862 -5.1303021498850425 46.94444444444444) '(14.77211629518312 -2.6047226650039703 47.22222222222222) "")
 (command "line" '(14.77211629518312 -2.6047226650039703 47.22222222222222) '(15.0 -1.8369701987210297e-14 47.5) "")
 (command "line" '(15.0 -1.8369701987210297e-14 47.5) '(14.772116295183125 2.6047226650039343 47.77777777777778) "")
 (command "line" '(14.772116295183125 2.6047226650039343 47.77777777777778) '(14.095389311788635 5.130302149885008 48.05555555555556) "")
 (command "line" '(14.095389311788635 5.130302149885008 48.05555555555556) '(12.990381056766594 7.499999999999976 48.33333333333333) "")
 (command "line" '(12.990381056766594 7.499999999999976 48.33333333333333) '(11.49066664678469 9.641814145298067 48.61111111111111) "")
 (command "line" '(11.49066664678469 9.641814145298067 48.61111111111111) '(9.641814145298076 11.490666646784684 48.88888888888889) "")
 (command "line" '(9.641814145298076 11.490666646784684 48.88888888888889) '(7.500000000000032 12.99038105676656 49.16666666666667) "")
 (command "line" '(7.500000000000032 12.99038105676656 49.16666666666667) '(5.1303021498850185 14.09538931178863 49.44444444444444) "")
 (command "line" '(5.1303021498850185 14.09538931178863 49.44444444444444) '(2.6047226650039974 14.772116295183114 49.72222222222222) "")
 (command "line" '(2.6047226650039974 14.772116295183114 49.72222222222222) '(-7.357165504432944e-15 15.0 50.0) "")
 (command "line" '(-7.357165504432944e-15 15.0 50.0) '(-2.6047226650039073 14.772116295183128 50.27777777777778) "")
 (command "line" '(-2.6047226650039073 14.772116295183128 50.27777777777778) '(-5.130302149885033 14.095389311788624 50.55555555555556) "")
 (command "line" '(-5.130302149885033 14.095389311788624 50.55555555555556) '(-7.499999999999953 12.990381056766607 50.83333333333333) "")
 (command "line" '(-7.499999999999953 12.990381056766607 50.83333333333333) '(-9.641814145298085 11.490666646784673 51.11111111111111) "")
 (command "line" '(-9.641814145298085 11.490666646784673 51.11111111111111) '(-11.4906666467847 9.641814145298056 51.38888888888889) "")
 (command "line" '(-11.4906666467847 9.641814145298056 51.38888888888889) '(-12.990381056766575 7.50000000000001 51.66666666666667) "")
 (command "line" '(-12.990381056766575 7.50000000000001 51.66666666666667) '(-14.09538931178864 5.130302149884994 51.94444444444444) "")
 (command "line" '(-14.09538931178864 5.130302149884994 51.94444444444444) '(-14.77211629518312 2.604722665003972 52.22222222222222) "")
 (command "line" '(-14.77211629518312 2.604722665003972 52.22222222222222) '(-15.0 7.349737736793884e-14 52.5) "")
 (command "line" '(-15.0 7.349737736793884e-14 52.5) '(-14.772116295183125 -2.6047226650039326 52.77777777777778) "")
 (command "line" '(-14.772116295183125 -2.6047226650039326 52.77777777777778) '(-14.095389311788653 -5.130302149884956 53.05555555555556) "")
 (command "line" '(-14.095389311788653 -5.130302149884956 53.05555555555556) '(-12.990381056766594 -7.499999999999974 53.33333333333333) "")
 (command "line" '(-12.990381056766594 -7.499999999999974 53.33333333333333) '(-11.490666646784724 -9.641814145298024 53.61111111111111) "")
 (command "line" '(-11.490666646784724 -9.641814145298024 53.61111111111111) '(-9.641814145298117 -11.490666646784648 53.88888888888889) "")
 (command "line" '(-9.641814145298117 -11.490666646784648 53.88888888888889) '(-7.499999999999988 -12.990381056766587 54.16666666666667) "")
 (command "line" '(-7.499999999999988 -12.990381056766587 54.16666666666667) '(-5.13030214988507 -14.095389311788612 54.44444444444444) "")
 (command "line" '(-5.13030214988507 -14.095389311788612 54.44444444444444) '(-2.604722665003947 -14.772116295183121 54.72222222222222) "")
 (command "line" '(-2.604722665003947 -14.772116295183121 54.72222222222222) '(-4.77705098762956e-14 -15.0 55.0) "")
 (command "line" '(-4.77705098762956e-14 -15.0 55.0) '(2.6047226650039574 -14.772116295183121 55.27777777777778) "")
 (command "line" '(2.6047226650039574 -14.772116295183121 55.27777777777778) '(5.13030214988498 -14.095389311788646 55.55555555555556) "")
 (command "line" '(5.13030214988498 -14.095389311788646 55.55555555555556) '(7.4999999999999964 -12.990381056766582 55.83333333333333) "")
 (command "line" '(7.4999999999999964 -12.990381056766582 55.83333333333333) '(9.641814145298044 -11.490666646784709 56.11111111111111) "")
 (command "line" '(9.641814145298044 -11.490666646784709 56.11111111111111) '(11.490666646784664 -9.641814145298097 56.38888888888889) "")
 (command "line" '(11.490666646784664 -9.641814145298097 56.38888888888889) '(12.990381056766601 -7.499999999999965 56.66666666666667) "")
 (command "line" '(12.990381056766601 -7.499999999999965 56.66666666666667) '(14.095389311788619 -5.130302149885046 56.94444444444444) "")
 (command "line" '(14.095389311788619 -5.130302149885046 56.94444444444444) '(14.772116295183126 -2.604722665003921 57.22222222222222) "")
 (command "line" '(14.772116295183126 -2.604722665003921 57.22222222222222) '(15.0 -2.2043642384652355e-14 57.5) "")
 (command "line" '(15.0 -2.2043642384652355e-14 57.5) '(14.772116295183135 2.604722665003878 57.77777777777778) "")
 (command "line" '(14.772116295183135 2.604722665003878 57.77777777777778) '(14.095389311788635 5.130302149885005 58.05555555555556) "")
 (command "line" '(14.095389311788635 5.130302149885005 58.05555555555556) '(12.990381056766623 7.499999999999927 58.33333333333333) "")
 (command "line" '(12.990381056766623 7.499999999999927 58.33333333333333) '(11.490666646784693 9.641814145298063 58.61111111111111) "")
 (command "line" '(11.490666646784693 9.641814145298063 58.61111111111111) '(9.641814145298078 11.49066664678468 58.88888888888889) "")
 (command "line" '(9.641814145298078 11.49066664678468 58.88888888888889) '(7.500000000000035 12.990381056766559 59.16666666666667) "")
 (command "line" '(7.500000000000035 12.990381056766559 59.16666666666667) '(5.130302149885021 14.09538931178863 59.44444444444444) "")
 (command "line" '(5.130302149885021 14.09538931178863 59.44444444444444) '(2.604722665004001 14.772116295183112 59.72222222222222) "")
 (command "line" '(2.604722665004001 14.772116295183112 59.72222222222222) '(-3.683225106990885e-15 15.0 60.0) "")
 (command "line" '(-3.683225106990885e-15 15.0 60.0) '(-2.6047226650039033 14.77211629518313 60.27777777777778) "")
 (command "line" '(-2.6047226650039033 14.77211629518313 60.27777777777778) '(-5.130302149885029 14.095389311788626 60.55555555555556) "")
 (command "line" '(-5.130302149885029 14.095389311788626 60.55555555555556) '(-7.499999999999949 12.990381056766608 60.83333333333333) "")
 (command "line" '(-7.499999999999949 12.990381056766608 60.83333333333333) '(-9.641814145298083 11.490666646784675 61.11111111111111) "")
 (command "line" '(-9.641814145298083 11.490666646784675 61.11111111111111) '(-11.490666646784696 9.641814145298058 61.38888888888889) "")
 (command "line" '(-11.490666646784696 9.641814145298058 61.38888888888889) '(-12.990381056766573 7.500000000000013 61.66666666666667) "")
 (command "line" '(-12.990381056766573 7.500000000000013 61.66666666666667) '(-14.095389311788638 5.130302149884997 61.94444444444444) "")
 (command "line" '(-14.095389311788638 5.130302149884997 61.94444444444444) '(-14.772116295183118 2.6047226650039756 62.22222222222222) "")
 (command "line" '(-14.772116295183118 2.6047226650039756 62.22222222222222) '(-15.0 -2.941009259863412e-14 62.5) "")
 (command "line" '(-15.0 -2.941009259863412e-14 62.5) '(-14.772116295183125 -2.6047226650039286 62.77777777777778) "")
 (command "line" '(-14.772116295183125 -2.6047226650039286 62.77777777777778) '(-14.095389311788654 -5.130302149884953 63.05555555555556) "")
 (command "line" '(-14.095389311788654 -5.130302149884953 63.05555555555556) '(-12.990381056766596 -7.499999999999972 63.33333333333333) "")
 (command "line" '(-12.990381056766596 -7.499999999999972 63.33333333333333) '(-11.490666646784728 -9.641814145298023 63.61111111111111) "")
 (command "line" '(-11.490666646784728 -9.641814145298023 63.61111111111111) '(-9.64181414529812 -11.490666646784645 63.88888888888889) "")
 (command "line" '(-9.64181414529812 -11.490666646784645 63.88888888888889) '(-7.49999999999999 -12.990381056766585 64.16666666666667) "")
 (command "line" '(-7.49999999999999 -12.990381056766585 64.16666666666667) '(-5.130302149885074 -14.09538931178861 64.44444444444444) "")
 (command "line" '(-5.130302149885074 -14.09538931178861 64.44444444444444) '(-2.6047226650039503 -14.772116295183121 64.72222222222223) "")
 (command "line" '(-2.6047226650039503 -14.772116295183121 64.72222222222223) '(-5.144445027373766e-14 -15.0 65.0) "")
 (command "line" '(-5.144445027373766e-14 -15.0 65.0) '(2.6047226650039543 -14.772116295183121 65.27777777777777) "")
 (command "line" '(2.6047226650039543 -14.772116295183121 65.27777777777777) '(5.130302149884977 -14.095389311788646 65.55555555555556) "")
 (command "line" '(5.130302149884977 -14.095389311788646 65.55555555555556) '(7.499999999999993 -12.990381056766584 65.83333333333333) "")
 (command "line" '(7.499999999999993 -12.990381056766584 65.83333333333333) '(9.64181414529804 -11.490666646784712 66.11111111111111) "")
 (command "line" '(9.64181414529804 -11.490666646784712 66.11111111111111) '(11.490666646784662 -9.6418141452981 66.38888888888889) "")
 (command "line" '(11.490666646784662 -9.6418141452981 66.38888888888889) '(12.990381056766598 -7.499999999999968 66.66666666666667) "")
 (command "line" '(12.990381056766598 -7.499999999999968 66.66666666666667) '(14.095389311788619 -5.130302149885049 66.94444444444444) "")
 (command "line" '(14.095389311788619 -5.130302149885049 66.94444444444444) '(14.772116295183126 -2.604722665003925 67.22222222222223) "")
 (command "line" '(14.772116295183126 -2.604722665003925 67.22222222222223) '(15.0 -2.5717582782094416e-14 67.5) "")
 (command "line" '(15.0 -2.5717582782094416e-14 67.5) '(14.772116295183135 2.6047226650038744 67.77777777777777) "")
 (command "line" '(14.772116295183135 2.6047226650038744 67.77777777777777) '(14.095389311788637 5.130302149885001 68.05555555555556) "")
 (command "line" '(14.095389311788637 5.130302149885001 68.05555555555556) '(12.990381056766624 7.499999999999924 68.33333333333333) "")
 (command "line" '(12.990381056766624 7.499999999999924 68.33333333333333) '(11.490666646784696 9.64181414529806 68.61111111111111) "")
 (command "line" '(11.490666646784696 9.64181414529806 68.61111111111111) '(9.641814145298081 11.490666646784678 68.88888888888889) "")
 (command "line" '(9.641814145298081 11.490666646784678 68.88888888888889) '(7.500000000000038 12.990381056766557 69.16666666666667) "")
 (command "line" '(7.500000000000038 12.990381056766557 69.16666666666667) '(5.130302149885025 14.095389311788628 69.44444444444444) "")
 (command "line" '(5.130302149885025 14.095389311788628 69.44444444444444) '(2.6047226650040045 14.772116295183112 69.72222222222223) "")
 (command "line" '(2.6047226650040045 14.772116295183112 69.72222222222223) '(-9.284709548825366e-18 15.0 70.0) "")
 (command "line" '(-9.284709548825366e-18 15.0 70.0) '(-2.6047226650038997 14.77211629518313 70.27777777777777) "")
 (command "line" '(-2.6047226650038997 14.77211629518313 70.27777777777777) '(-5.130302149885025 14.095389311788628 70.55555555555556) "")
 (command "line" '(-5.130302149885025 14.095389311788628 70.55555555555556) '(-7.499999999999946 12.99038105676661 70.83333333333333) "")
 (command "line" '(-7.499999999999946 12.99038105676661 70.83333333333333) '(-9.641814145298081 11.490666646784678 71.11111111111111) "")
 (command "line" '(-9.641814145298081 11.490666646784678 71.11111111111111) '(-11.490666646784696 9.64181414529806 71.38888888888889) "")
 (command "line" '(-11.490666646784696 9.64181414529806 71.38888888888889) '(-12.990381056766571 7.500000000000017 71.66666666666667) "")
 (command "line" '(-12.990381056766571 7.500000000000017 71.66666666666667) '(-14.095389311788637 5.130302149885001 71.94444444444444) "")
 (command "line" '(-14.095389311788637 5.130302149885001 71.94444444444444) '(-14.772116295183118 2.6047226650039796 72.22222222222223) "")
 (command "line" '(-14.772116295183118 2.6047226650039796 72.22222222222223) '(-15.0 8.084525816282296e-14 72.5) "")
 (command "line" '(-15.0 8.084525816282296e-14 72.5) '(-14.772116295183126 -2.604722665003925 72.77777777777777) "")
 (command "line" '(-14.772116295183126 -2.604722665003925 72.77777777777777) '(-14.095389311788654 -5.130302149884949 73.05555555555556) "")
 (command "line" '(-14.095389311788654 -5.130302149884949 73.05555555555556) '(-12.990381056766598 -7.499999999999968 73.33333333333333) "")
 (command "line" '(-12.990381056766598 -7.499999999999968 73.33333333333333) '(-11.49066664678473 -9.641814145298019 73.61111111111111) "")
 (command "line" '(-11.49066664678473 -9.641814145298019 73.61111111111111) '(-9.641814145298122 -11.490666646784643 73.88888888888889) "")
 (command "line" '(-9.641814145298122 -11.490666646784643 73.88888888888889) '(-7.499999999999993 -12.990381056766584 74.16666666666667) "")
 (command "line" '(-7.499999999999993 -12.990381056766584 74.16666666666667) '(-5.130302149885077 -14.09538931178861 74.44444444444444) "")
 (command "line" '(-5.130302149885077 -14.09538931178861 74.44444444444444) '(-2.6047226650039543 -14.772116295183121 74.72222222222223) "")
 (command "line" '(-2.6047226650039543 -14.772116295183121 74.72222222222223) '(-5.5118390671179717e-14 -15.0 75.0) "")
 (command "line" '(-5.5118390671179717e-14 -15.0 75.0) '(2.6047226650039503 -14.772116295183121 75.27777777777777) "")
 (command "line" '(2.6047226650039503 -14.772116295183121 75.27777777777777) '(5.130302149884973 -14.095389311788647 75.55555555555556) "")
 (command "line" '(5.130302149884973 -14.095389311788647 75.55555555555556) '(7.49999999999999 -12.990381056766585 75.83333333333333) "")
 (command "line" '(7.49999999999999 -12.990381056766585 75.83333333333333) '(9.641814145298039 -11.490666646784714 76.11111111111111) "")
 (command "line" '(9.641814145298039 -11.490666646784714 76.11111111111111) '(11.49066664678466 -9.641814145298104 76.38888888888889) "")
 (command "line" '(11.49066664678466 -9.641814145298104 76.38888888888889) '(12.990381056766596 -7.499999999999972 76.66666666666667) "")
 (command "line" '(12.990381056766596 -7.499999999999972 76.66666666666667) '(14.095389311788619 -5.130302149885053 76.94444444444444) "")
 (command "line" '(14.095389311788619 -5.130302149885053 76.94444444444444) '(14.772116295183125 -2.6047226650039286 77.22222222222223) "")
 (command "line" '(14.772116295183125 -2.6047226650039286 77.22222222222223) '(15.0 -2.939152317953648e-14 77.5) "")
 (command "line" '(15.0 -2.939152317953648e-14 77.5) '(14.772116295183118 2.6047226650039756 77.77777777777777) "")
 (command "line" '(14.772116295183118 2.6047226650039756 77.77777777777777) '(14.095389311788638 5.130302149884997 78.05555555555556) "")
 (command "line" '(14.095389311788638 5.130302149884997 78.05555555555556) '(12.990381056766573 7.500000000000013 78.33333333333333) "")
 (command "line" '(12.990381056766573 7.500000000000013 78.33333333333333) '(11.490666646784696 9.641814145298058 78.61111111111111) "")
 (command "line" '(11.490666646784696 9.641814145298058 78.61111111111111) '(9.641814145298083 11.490666646784675 78.88888888888889) "")
 (command "line" '(9.641814145298083 11.490666646784675 78.88888888888889) '(7.500000000000042 12.990381056766555 79.16666666666667) "")
 (command "line" '(7.500000000000042 12.990381056766555 79.16666666666667) '(5.130302149885029 14.095389311788626 79.44444444444444) "")
 (command "line" '(5.130302149885029 14.095389311788626 79.44444444444444) '(2.604722665004008 14.772116295183112 79.72222222222223) "")
 (command "line" '(2.604722665004008 14.772116295183112 79.72222222222223) '(3.664655687893234e-15 15.0 80.0) "")
 (command "line" '(3.664655687893234e-15 15.0 80.0) '(-2.604722665004001 14.772116295183112 80.27777777777779) "")
 (command "line" '(-2.604722665004001 14.772116295183112 80.27777777777779) '(-5.130302149885021 14.09538931178863 80.55555555555556) "")
 (command "line" '(-5.130302149885021 14.09538931178863 80.55555555555556) '(-7.500000000000035 12.990381056766559 80.83333333333334) "")
 (command "line" '(-7.500000000000035 12.990381056766559 80.83333333333334) '(-9.641814145298078 11.49066664678468 81.11111111111111) "")
 (command "line" '(-9.641814145298078 11.49066664678468 81.11111111111111) '(-11.490666646784693 9.641814145298063 81.38888888888889) "")
 (command "line" '(-11.490666646784693 9.641814145298063 81.38888888888889) '(-12.990381056766516 7.500000000000112 81.66666666666666) "")
 (command "line" '(-12.990381056766516 7.500000000000112 81.66666666666666) '(-14.095389311788635 5.130302149885005 81.94444444444444) "")
 (command "line" '(-14.095389311788635 5.130302149885005 81.94444444444444) '(-14.772116295183096 2.604722665004088 82.22222222222221) "")
 (command "line" '(-14.772116295183096 2.604722665004088 82.22222222222221) '(-15.0 -2.2062211803750007e-14 82.5) "")
 (command "line" '(-15.0 -2.2062211803750007e-14 82.5) '(-14.772116295183109 -2.6047226650040267 82.77777777777779) "")
 (command "line" '(-14.772116295183109 -2.6047226650040267 82.77777777777779) '(-14.095389311788656 -5.130302149884946 83.05555555555556) "")
 (command "line" '(-14.095389311788656 -5.130302149884946 83.05555555555556) '(-12.990381056766548 -7.500000000000057 83.33333333333334) "")
 (command "line" '(-12.990381056766548 -7.500000000000057 83.33333333333334) '(-11.490666646784733 -9.641814145298016 83.61111111111111) "")
 (command "line" '(-11.490666646784733 -9.641814145298016 83.61111111111111) '(-9.641814145298126 -11.490666646784641 83.88888888888889) "")
 (command "line" '(-9.641814145298126 -11.490666646784641 83.88888888888889) '(-7.500000000000088 -12.990381056766529 84.16666666666666) "")
 (command "line" '(-7.500000000000088 -12.990381056766529 84.16666666666666) '(-5.130302149885081 -14.095389311788608 84.44444444444444) "")
 (command "line" '(-5.130302149885081 -14.095389311788608 84.44444444444444) '(-2.6047226650040627 -14.772116295183102 84.72222222222221) "")
 (command "line" '(-2.6047226650040627 -14.772116295183102 84.72222222222221) '(-5.879233106862178e-14 -15.0 85.0) "")
 (command "line" '(-5.879233106862178e-14 -15.0 85.0) '(2.604722665003947 -14.772116295183121 85.27777777777779) "")
 (command "line" '(2.604722665003947 -14.772116295183121 85.27777777777779) '(5.13030214988497 -14.095389311788647 85.55555555555556) "")
 (command "line" '(5.13030214988497 -14.095389311788647 85.55555555555556) '(7.499999999999988 -12.990381056766587 85.83333333333334) "")
 (command "line" '(7.499999999999988 -12.990381056766587 85.83333333333334) '(9.641814145298035 -11.490666646784717 86.11111111111111) "")
 (command "line" '(9.641814145298035 -11.490666646784717 86.11111111111111) '(11.490666646784657 -9.641814145298106 86.38888888888889) "")
 (command "line" '(11.490666646784657 -9.641814145298106 86.38888888888889) '(12.990381056766541 -7.500000000000067 86.66666666666666) "")
 (command "line" '(12.990381056766541 -7.500000000000067 86.66666666666666) '(14.095389311788617 -5.130302149885057 86.94444444444444) "")
 (command "line" '(14.095389311788617 -5.130302149885057 86.94444444444444) '(14.772116295183107 -2.6047226650040374 87.22222222222221) "")
 (command "line" '(14.772116295183107 -2.6047226650040374 87.22222222222221) '(15.0 -3.306546357697854e-14 87.5) "")
 (command "line" '(15.0 -3.306546357697854e-14 87.5) '(14.77211629518312 2.604722665003972 87.77777777777779) "")
 (command "line" '(14.77211629518312 2.604722665003972 87.77777777777779) '(14.09538931178864 5.130302149884994 88.05555555555556) "")
 (command "line" '(14.09538931178864 5.130302149884994 88.05555555555556) '(12.990381056766575 7.50000000000001 88.33333333333334) "")
 (command "line" '(12.990381056766575 7.50000000000001 88.33333333333334) '(11.4906666467847 9.641814145298056 88.61111111111111) "")
 (command "line" '(11.4906666467847 9.641814145298056 88.61111111111111) '(9.641814145298085 11.490666646784673 88.88888888888889) "")
 (command "line" '(9.641814145298085 11.490666646784673 88.88888888888889) '(7.500000000000045 12.990381056766553 89.16666666666666) "")
 (command "line" '(7.500000000000045 12.990381056766553 89.16666666666666) '(5.130302149885033 14.095389311788624 89.44444444444444) "")
 (command "line" '(5.130302149885033 14.095389311788624 89.44444444444444) '(2.604722665004012 14.77211629518311 89.72222222222221) "")
 (command "line" '(2.604722665004012 14.77211629518311 89.72222222222221) '(7.338596085335294e-15 15.0 90.0) "")
 (command "line" '(7.338596085335294e-15 15.0 90.0) '(-2.6047226650039974 14.772116295183114 90.27777777777779) "")
 (command "line" '(-2.6047226650039974 14.772116295183114 90.27777777777779) '(-5.1303021498850185 14.09538931178863 90.55555555555556) "")
 (command "line" '(-5.1303021498850185 14.09538931178863 90.55555555555556) '(-7.500000000000032 12.99038105676656 90.83333333333334) "")
 (command "line" '(-7.500000000000032 12.99038105676656 90.83333333333334) '(-9.641814145298076 11.490666646784684 91.11111111111111) "")
 (command "line" '(-9.641814145298076 11.490666646784684 91.11111111111111) '(-11.49066664678469 9.641814145298067 91.38888888888889) "")
 (command "line" '(-11.49066664678469 9.641814145298067 91.38888888888889) '(-12.990381056766514 7.500000000000115 91.66666666666666) "")
 (command "line" '(-12.990381056766514 7.500000000000115 91.66666666666666) '(-14.095389311788635 5.130302149885008 91.94444444444444) "")
 (command "line" '(-14.095389311788635 5.130302149885008 91.94444444444444) '(-14.772116295183096 2.6047226650040916 92.22222222222221) "")
 (command "line" '(-14.772116295183096 2.6047226650040916 92.22222222222221) '(-15.0 8.819313895770708e-14 92.5) "")
 (command "line" '(-15.0 8.819313895770708e-14 92.5) '(-14.772116295183109 -2.6047226650040227 92.77777777777779) "")
 (command "line" '(-14.772116295183109 -2.6047226650040227 92.77777777777779) '(-14.095389311788658 -5.130302149884942 93.05555555555556) "")
 (command "line" '(-14.095389311788658 -5.130302149884942 93.05555555555556) '(-12.990381056766548 -7.500000000000053 93.33333333333334) "")
 (command "line" '(-12.990381056766548 -7.500000000000053 93.33333333333334) '(-11.490666646784735 -9.641814145298012 93.61111111111111) "")
 (command "line" '(-11.490666646784735 -9.641814145298012 93.61111111111111) '(-9.64181414529813 -11.49066664678464 93.88888888888889) "")
 (command "line" '(-9.64181414529813 -11.49066664678464 93.88888888888889) '(-7.5000000000000915 -12.990381056766527 94.16666666666666) "")
 (command "line" '(-7.5000000000000915 -12.990381056766527 94.16666666666666) '(-5.130302149885084 -14.095389311788606 94.44444444444444) "")
 (command "line" '(-5.130302149885084 -14.095389311788606 94.44444444444444) '(-2.6047226650040662 -14.772116295183102 94.72222222222221) "")
 (command "line" '(-2.6047226650040662 -14.772116295183102 94.72222222222221) '(-6.246627146606384e-14 -15.0 95.0) "")
 (command "line" '(-6.246627146606384e-14 -15.0 95.0) '(2.6047226650039432 -14.772116295183123 95.27777777777779) "")
 (command "line" '(2.6047226650039432 -14.772116295183123 95.27777777777779) '(5.130302149884967 -14.095389311788649 95.55555555555556) "")
 (command "line" '(5.130302149884967 -14.095389311788649 95.55555555555556) '(7.499999999999984 -12.990381056766589 95.83333333333334) "")
 (command "line" '(7.499999999999984 -12.990381056766589 95.83333333333334) '(9.641814145298031 -11.49066664678472 96.11111111111111) "")
 (command "line" '(9.641814145298031 -11.49066664678472 96.11111111111111) '(11.490666646784655 -9.64181414529811 96.38888888888889) "")
 (command "line" '(11.490666646784655 -9.64181414529811 96.38888888888889) '(12.99038105676654 -7.50000000000007 96.66666666666666) "")
 (command "line" '(12.99038105676654 -7.50000000000007 96.66666666666666) '(14.095389311788615 -5.130302149885059 96.94444444444444) "")
 (command "line" '(14.095389311788615 -5.130302149885059 96.94444444444444) '(14.772116295183105 -2.604722665004041 97.22222222222221) "")
 (command "line" '(14.772116295183105 -2.604722665004041 97.22222222222221) '(15.0 -3.6739403974420595e-14 97.5) "")
 (command "line" '(15.0 -3.6739403974420595e-14 97.5) '(14.77211629518312 2.6047226650039685 97.77777777777779) "")
 (command "line" '(14.77211629518312 2.6047226650039685 97.77777777777779) '(14.09538931178864 5.130302149884991 98.05555555555556) "")
 (command "line" '(14.09538931178864 5.130302149884991 98.05555555555556) '(12.990381056766577 7.500000000000007 98.33333333333334) "")
 (command "line" '(12.990381056766577 7.500000000000007 98.33333333333334) '(11.490666646784701 9.641814145298053 98.61111111111111) "")
 (command "line" '(11.490666646784701 9.641814145298053 98.61111111111111) '(9.641814145298088 11.490666646784671 98.88888888888889) "")
 (command "line" '(9.641814145298088 11.490666646784671 98.88888888888889) '(7.500000000000048 12.990381056766552 99.16666666666666) "")
 (command "line" '(7.500000000000048 12.990381056766552 99.16666666666666) '(5.130302149885035 14.095389311788624 99.44444444444444) "")
 (command "line" '(5.130302149885035 14.095389311788624 99.44444444444444) '(2.604722665004015 14.77211629518311 99.72222222222221) "")
 (command "line" '(2.604722665004015 14.77211629518311 99.72222222222221) '(1.1759394684679237e-13 15.0 100.0) "")
 (command "line" '(1.1759394684679237e-13 15.0 100.0) '(-2.604722665003994 14.772116295183114 100.27777777777779) "")
 (command "line" '(-2.604722665003994 14.772116295183114 100.27777777777779) '(-5.130302149885015 14.095389311788631 100.55555555555556) "")
 (command "line" '(-5.130302149885015 14.095389311788631 100.55555555555556) '(-7.499999999999936 12.990381056766616 100.83333333333334) "")
 (command "line" '(-7.499999999999936 12.990381056766616 100.83333333333334) '(-9.64181414529799 11.490666646784753 101.11111111111111) "")
 (command "line" '(-9.64181414529799 11.490666646784753 101.11111111111111) '(-11.490666646784689 9.641814145298069 101.38888888888889) "")
 (command "line" '(-11.490666646784689 9.641814145298069 101.38888888888889) '(-12.990381056766566 7.500000000000025 101.66666666666666) "")
 (command "line" '(-12.990381056766566 7.500000000000025 101.66666666666666) '(-14.095389311788596 5.130302149885112 101.94444444444444) "")
 (command "line" '(-14.095389311788596 5.130302149885112 101.94444444444444) '(-14.772116295183096 2.604722665004095 102.22222222222221) "")
 (command "line" '(-14.772116295183096 2.604722665004095 102.22222222222221) '(-15.0 -1.471433100886589e-14 102.5) "")
 (command "line" '(-15.0 -1.471433100886589e-14 102.5) '(-14.772116295183128 -2.6047226650039144 102.77777777777779) "")
 (command "line" '(-14.772116295183128 -2.6047226650039144 102.77777777777779) '(-14.09538931178866 -5.1303021498849395 103.05555555555556) "")
 (command "line" '(-14.09538931178866 -5.1303021498849395 103.05555555555556) '(-12.99038105676655 -7.5000000000000515 103.33333333333334) "")
 (command "line" '(-12.99038105676655 -7.5000000000000515 103.33333333333334) '(-11.490666646784668 -9.641814145298092 103.61111111111111) "")
 (command "line" '(-11.490666646784668 -9.641814145298092 103.61111111111111) '(-9.641814145298133 -11.490666646784636 103.88888888888889) "")
 (command "line" '(-9.641814145298133 -11.490666646784636 103.88888888888889) '(-7.500000000000095 -12.990381056766523 104.16666666666666) "")
 (command "line" '(-7.500000000000095 -12.990381056766523 104.16666666666666) '(-5.1303021498849875 -14.095389311788642 104.44444444444444) "")
 (command "line" '(-5.1303021498849875 -14.095389311788642 104.44444444444444) '(-2.604722665003965 -14.77211629518312 104.72222222222221) "")
 (command "line" '(-2.604722665003965 -14.77211629518312 104.72222222222221) '(-6.61402118635059e-14 -15.0 105.0) "")
 (command "line" '(-6.61402118635059e-14 -15.0 105.0) '(2.6047226650040445 -14.772116295183105 105.27777777777779) "")
 (command "line" '(2.6047226650040445 -14.772116295183105 105.27777777777779) '(5.130302149885063 -14.095389311788615 105.55555555555556) "")
 (command "line" '(5.130302149885063 -14.095389311788615 105.55555555555556) '(7.4999999999999805 -12.99038105676659 105.83333333333334) "")
 (command "line" '(7.4999999999999805 -12.99038105676659 105.83333333333334) '(9.64181414529803 -11.490666646784721 106.11111111111111) "")
 (command "line" '(9.64181414529803 -11.490666646784721 106.11111111111111) '(11.490666646784721 -9.64181414529803 106.38888888888889) "")
 (command "line" '(11.490666646784721 -9.64181414529803 106.38888888888889) '(12.990381056766484 -7.500000000000165 106.66666666666666) "")
 (command "line" '(12.990381056766484 -7.500000000000165 106.66666666666666) '(14.095389311788615 -5.130302149885063 106.94444444444444) "")
 (command "line" '(14.095389311788615 -5.130302149885063 106.94444444444444) '(14.772116295183105 -2.6047226650040445 107.22222222222221) "")
 (command "line" '(14.772116295183105 -2.6047226650040445 107.22222222222221) '(15.0 -1.4699475473587768e-13 107.5) "")
 (command "line" '(15.0 -1.4699475473587768e-13 107.5) '(14.77211629518312 2.604722665003965 107.77777777777779) "")
 (command "line" '(14.77211629518312 2.604722665003965 107.77777777777779) '(14.095389311788642 5.1303021498849875 108.05555555555556) "")
 (command "line" '(14.095389311788642 5.1303021498849875 108.05555555555556) '(12.990381056766523 7.500000000000095 108.33333333333334) "")
 (command "line" '(12.990381056766523 7.500000000000095 108.33333333333334) '(11.490666646784774 9.641814145297968 108.61111111111111) "")
 (command "line" '(11.490666646784774 9.641814145297968 108.61111111111111) '(9.641814145298092 11.490666646784668 108.88888888888889) "")
 (command "line" '(9.641814145298092 11.490666646784668 108.88888888888889) '(7.5000000000000515 12.99038105676655 109.16666666666666) "")
 (command "line" '(7.5000000000000515 12.99038105676655 109.16666666666666) '(5.130302149885139 14.095389311788587 109.44444444444444) "")
 (command "line" '(5.130302149885139 14.095389311788587 109.44444444444444) '(2.604722665004124 14.77211629518309 109.72222222222221) "")
 (command "line" '(2.604722665004124 14.77211629518309 109.72222222222221) '(1.4686476880219412e-14 15.0 110.0) "")
 (command "line" '(1.4686476880219412e-14 15.0 110.0) '(-2.6047226650038855 14.772116295183134 110.27777777777779) "")
 (command "line" '(-2.6047226650038855 14.772116295183134 110.27777777777779) '(-5.130302149884912 14.09538931178867 110.55555555555556) "")
 (command "line" '(-5.130302149884912 14.09538931178867 110.55555555555556) '(-7.500000000000025 12.990381056766566 110.83333333333334) "")
 (command "line" '(-7.500000000000025 12.990381056766566 110.83333333333334) '(-9.641814145298069 11.490666646784689 111.11111111111111) "")
 (command "line" '(-9.641814145298069 11.490666646784689 111.11111111111111) '(-11.490666646784616 9.641814145298154 111.38888888888889) "")
 (command "line" '(-11.490666646784616 9.641814145298154 111.38888888888889) '(-12.990381056766509 7.500000000000122 111.66666666666666) "")
 (command "line" '(-12.990381056766509 7.500000000000122 111.66666666666666) '(-14.095389311788631 5.130302149885015 111.94444444444444) "")
 (command "line" '(-14.095389311788631 5.130302149885015 111.94444444444444) '(-14.772116295183114 2.604722665003994 112.22222222222221) "")
 (command "line" '(-14.772116295183114 2.604722665003994 112.22222222222221) '(-15.0 9.55410197525912e-14 112.5) "")
 (command "line" '(-15.0 9.55410197525912e-14 112.5) '(-14.77211629518311 -2.6047226650040156 112.77777777777779) "")
 (command "line" '(-14.77211629518311 -2.6047226650040156 112.77777777777779) '(-14.095389311788624 -5.130302149885035 113.05555555555556) "")
 (command "line" '(-14.095389311788624 -5.130302149885035 113.05555555555556) '(-12.990381056766605 -7.499999999999955 113.33333333333334) "")
 (command "line" '(-12.990381056766605 -7.499999999999955 113.33333333333334) '(-11.49066664678474 -9.641814145298007 113.61111111111111) "")
 (command "line" '(-11.49066664678474 -9.641814145298007 113.61111111111111) '(-9.641814145298053 -11.490666646784701 113.88888888888889) "")
 (command "line" '(-9.641814145298053 -11.490666646784701 113.88888888888889) '(-7.500000000000007 -12.990381056766577 114.16666666666666) "")
 (command "line" '(-7.500000000000007 -12.990381056766577 114.16666666666666) '(-5.1303021498850905 -14.095389311788605 114.44444444444444) "")
 (command "line" '(-5.1303021498850905 -14.095389311788605 114.44444444444444) '(-2.604722665004074 -14.7721162951831 114.72222222222221) "")
 (command "line" '(-2.604722665004074 -14.7721162951831 114.72222222222221) '(3.6767258103067074e-14 -15.0 115.0) "")
 (command "line" '(3.6767258103067074e-14 -15.0 115.0) '(2.6047226650039357 -14.772116295183123 115.27777777777779) "")
 (command "line" '(2.6047226650039357 -14.772116295183123 115.27777777777779) '(5.13030214988496 -14.09538931178865 115.55555555555556) "")
 (command "line" '(5.13030214988496 -14.09538931178865 115.55555555555556) '(7.50000000000007 -12.99038105676654 115.83333333333334) "")
 (command "line" '(7.50000000000007 -12.99038105676654 115.83333333333334) '(9.64181414529811 -11.490666646784655 116.11111111111111) "")
 (command "line" '(9.64181414529811 -11.490666646784655 116.11111111111111) '(11.49066664678465 -9.641814145298113 116.38888888888889) "")
 (command "line" '(11.49066664678465 -9.641814145298113 116.38888888888889) '(12.990381056766536 -7.500000000000076 116.66666666666666) "")
 (command "line" '(12.990381056766536 -7.500000000000076 116.66666666666666) '(14.095389311788649 -5.130302149884967 116.94444444444444) "")
 (command "line" '(14.095389311788649 -5.130302149884967 116.94444444444444) '(14.772116295183086 -2.6047226650041533 117.22222222222221) "")
 (command "line" '(14.772116295183086 -2.6047226650041533 117.22222222222221) '(15.0 -4.408728476930471e-14 117.5) "")
 (command "line" '(15.0 -4.408728476930471e-14 117.5) '(14.772116295183102 2.6047226650040662 117.77777777777779) "")
 (command "line" '(14.772116295183102 2.6047226650040662 117.77777777777779) '(14.09538931178868 5.1303021498848835 118.05555555555556) "")
 (command "line" '(14.09538931178868 5.1303021498848835 118.05555555555556) '(12.990381056766578 7.5 118.33333333333334) "")
 (command "line" '(12.990381056766578 7.5 118.33333333333334) '(11.490666646784707 9.641814145298047 118.61111111111111) "")
 (command "line" '(11.490666646784707 9.641814145298047 118.61111111111111) '(9.641814145298175 11.490666646784598 118.88888888888889) "")
 (command "line" '(9.641814145298175 11.490666646784598 118.88888888888889) '(7.5000000000001465 12.990381056766495 119.16666666666666) "")
 (command "line" '(7.5000000000001465 12.990381056766495 119.16666666666666) '(5.1303021498850425 14.09538931178862 119.44444444444444) "")
 (command "line" '(5.1303021498850425 14.09538931178862 119.44444444444444) '(2.6047226650040227 14.772116295183109 119.72222222222221) "")
 (command "line" '(2.6047226650040227 14.772116295183109 119.72222222222221) '(1.249418276416765e-13 15.0 120.0) "")
 (command "line" '(1.249418276416765e-13 15.0 120.0) '(-2.6047226650039867 14.772116295183116 120.27777777777779) "")
 (command "line" '(-2.6047226650039867 14.772116295183116 120.27777777777779) '(-5.130302149885008 14.095389311788635 120.55555555555556) "")
 (command "line" '(-5.130302149885008 14.095389311788635 120.55555555555556) '(-7.49999999999993 12.990381056766621 120.83333333333334) "")
 (command "line" '(-7.49999999999993 12.990381056766621 120.83333333333334) '(-9.641814145297985 11.490666646784758 121.11111111111111) "")
 (command "line" '(-9.641814145297985 11.490666646784758 121.11111111111111) '(-11.490666646784684 9.641814145298076 121.38888888888889) "")
 (command "line" '(-11.490666646784684 9.641814145298076 121.38888888888889) '(-12.99038105676656 7.500000000000032 121.66666666666666) "")
 (command "line" '(-12.99038105676656 7.500000000000032 121.66666666666666) '(-14.095389311788594 5.130302149885118 121.94444444444444) "")
 (command "line" '(-14.095389311788594 5.130302149885118 121.94444444444444) '(-14.772116295183096 2.604722665004102 122.22222222222221) "")
 (command "line" '(-14.772116295183096 2.604722665004102 122.22222222222221) '(-15.0 -7.36645021398177e-15 122.5) "")
 (command "line" '(-15.0 -7.36645021398177e-15 122.5) '(-14.772116295183128 -2.6047226650039073 122.77777777777779) "")
 (command "line" '(-14.772116295183128 -2.6047226650039073 122.77777777777779) '(-14.095389311788662 -5.1303021498849315 123.05555555555556) "")
 (command "line" '(-14.095389311788662 -5.1303021498849315 123.05555555555556) '(-12.990381056766553 -7.500000000000045 123.33333333333334) "")
 (command "line" '(-12.990381056766553 -7.500000000000045 123.33333333333334) '(-11.490666646784673 -9.641814145298085 123.61111111111111) "")
 (command "line" '(-11.490666646784673 -9.641814145298085 123.61111111111111) '(-9.641814145298136 -11.490666646784632 123.88888888888889) "")
 (command "line" '(-9.641814145298136 -11.490666646784632 123.88888888888889) '(-7.500000000000101 -12.990381056766521 124.16666666666666) "")
 (command "line" '(-7.500000000000101 -12.990381056766521 124.16666666666666) '(-5.130302149884994 -14.09538931178864 124.44444444444444) "")
 (command "line" '(-5.130302149884994 -14.09538931178864 124.44444444444444) '(-2.604722665003972 -14.77211629518312 124.72222222222221) "")
 (command "line" '(-2.604722665003972 -14.77211629518312 124.72222222222221) '(-7.348809265839001e-14 -15.0 125.0) "")
 (command "line" '(-7.348809265839001e-14 -15.0 125.0) '(2.6047226650040374 -14.772116295183107 125.27777777777779) "")
 (command "line" '(2.6047226650040374 -14.772116295183107 125.27777777777779) '(5.130302149885057 -14.095389311788617 125.55555555555556) "")
 (command "line" '(5.130302149885057 -14.095389311788617 125.55555555555556) '(7.499999999999974 -12.990381056766594 125.83333333333334) "")
 (command "line" '(7.499999999999974 -12.990381056766594 125.83333333333334) '(9.641814145298024 -11.490666646784724 126.11111111111111) "")
 (command "line" '(9.641814145298024 -11.490666646784724 126.11111111111111) '(11.490666646784717 -9.641814145298035 126.38888888888889) "")
 (command "line" '(11.490666646784717 -9.641814145298035 126.38888888888889) '(12.99038105676648 -7.500000000000171 126.66666666666666) "")
 (command "line" '(12.99038105676648 -7.500000000000171 126.66666666666666) '(14.095389311788612 -5.13030214988507 126.94444444444444) "")
 (command "line" '(14.095389311788612 -5.13030214988507 126.94444444444444) '(14.772116295183103 -2.6047226650040516 127.22222222222221) "")
 (command "line" '(14.772116295183103 -2.6047226650040516 127.22222222222221) '(15.0 5.882018519726824e-14 127.5) "")
 (command "line" '(15.0 5.882018519726824e-14 127.5) '(14.772116295183121 2.6047226650039574 127.77777777777779) "")
 (command "line" '(14.772116295183121 2.6047226650039574 127.77777777777779) '(14.095389311788646 5.13030214988498 128.05555555555554) "")
 (command "line" '(14.095389311788646 5.13030214988498 128.05555555555554) '(12.990381056766529 7.50000000000009 128.33333333333334) "")
 (command "line" '(12.990381056766529 7.50000000000009 128.33333333333334) '(11.490666646784776 9.641814145297962 128.61111111111111) "")
 (command "line" '(11.490666646784776 9.641814145297962 128.61111111111111) '(9.641814145298097 11.490666646784664 128.88888888888889) "")
 (command "line" '(9.641814145298097 11.490666646784664 128.88888888888889) '(7.500000000000057 12.990381056766548 129.16666666666666) "")
 (command "line" '(7.500000000000057 12.990381056766548 129.16666666666666) '(5.130302149885146 14.095389311788583 129.44444444444446) "")
 (command "line" '(5.130302149885146 14.095389311788583 129.44444444444446) '(2.6047226650041315 14.77211629518309 129.72222222222223) "")
 (command "line" '(2.6047226650041315 14.77211629518309 129.72222222222223) '(2.2034357675103534e-14 15.0 130.0) "")
 (command "line" '(2.2034357675103534e-14 15.0 130.0) '(-2.604722665003878 14.772116295183135 130.27777777777777) "")
 (command "line" '(-2.604722665003878 14.772116295183135 130.27777777777777) '(-5.130302149884904 14.095389311788672 130.55555555555554) "")
 (command "line" '(-5.130302149884904 14.095389311788672 130.55555555555554) '(-7.500000000000019 12.99038105676657 130.83333333333334) "")
 (command "line" '(-7.500000000000019 12.99038105676657 130.83333333333334) '(-9.641814145298063 11.490666646784693 131.11111111111111) "")
 (command "line" '(-9.641814145298063 11.490666646784693 131.11111111111111) '(-11.490666646784613 9.64181414529816 131.38888888888889) "")
 (command "line" '(-11.490666646784613 9.64181414529816 131.38888888888889) '(-12.990381056766505 7.500000000000126 131.66666666666666) "")
 (command "line" '(-12.990381056766505 7.500000000000126 131.66666666666666) '(-14.09538931178863 5.130302149885021 131.94444444444446) "")
 (command "line" '(-14.09538931178863 5.130302149885021 131.94444444444446) '(-14.772116295183112 2.604722665004001 132.22222222222223) "")
 (command "line" '(-14.772116295183112 2.604722665004001 132.22222222222223) '(-15.0 1.0288890054747532e-13 132.5) "")
 (command "line" '(-15.0 1.0288890054747532e-13 132.5) '(-14.772116295183112 -2.604722665004008 132.77777777777777) "")
 (command "line" '(-14.772116295183112 -2.604722665004008 132.77777777777777) '(-14.095389311788626 -5.130302149885029 133.05555555555554) "")
 (command "line" '(-14.095389311788626 -5.130302149885029 133.05555555555554) '(-12.990381056766608 -7.499999999999949 133.33333333333334) "")
 (command "line" '(-12.990381056766608 -7.499999999999949 133.33333333333334) '(-11.490666646784746 -9.641814145298003 133.61111111111111) "")
 (command "line" '(-11.490666646784746 -9.641814145298003 133.61111111111111) '(-9.641814145298058 -11.490666646784696 133.88888888888889) "")
 (command "line" '(-9.641814145298058 -11.490666646784696 133.88888888888889) '(-7.500000000000013 -12.990381056766573 134.16666666666666) "")
 (command "line" '(-7.500000000000013 -12.990381056766573 134.16666666666666) '(-5.1303021498850985 -14.095389311788601 134.44444444444446) "")
 (command "line" '(-5.1303021498850985 -14.095389311788601 134.44444444444446) '(-2.604722665004081 -14.772116295183098 134.72222222222223) "")
 (command "line" '(-2.604722665004081 -14.772116295183098 134.72222222222223) '(2.941937730818295e-14 -15.0 135.0) "")
 (command "line" '(2.941937730818295e-14 -15.0 135.0) '(2.6047226650039286 -14.772116295183125 135.27777777777777) "")
 (command "line" '(2.6047226650039286 -14.772116295183125 135.27777777777777) '(5.130302149884953 -14.095389311788654 135.55555555555554) "")
 (command "line" '(5.130302149884953 -14.095389311788654 135.55555555555554) '(7.500000000000063 -12.990381056766543 135.83333333333334) "")
 (command "line" '(7.500000000000063 -12.990381056766543 135.83333333333334) '(9.641814145298104 -11.490666646784659 136.11111111111111) "")
 (command "line" '(9.641814145298104 -11.490666646784659 136.11111111111111) '(11.490666646784645 -9.64181414529812 136.38888888888889) "")
 (command "line" '(11.490666646784645 -9.64181414529812 136.38888888888889) '(12.990381056766532 -7.5000000000000835 136.66666666666666) "")
 (command "line" '(12.990381056766532 -7.5000000000000835 136.66666666666666) '(14.095389311788647 -5.130302149884973 136.94444444444446) "")
 (command "line" '(14.095389311788647 -5.130302149884973 136.94444444444446) '(14.772116295183086 -2.6047226650041604 137.22222222222223) "")
 (command "line" '(14.772116295183086 -2.6047226650041604 137.22222222222223) '(15.0 -5.143516556418883e-14 137.5) "")
 (command "line" '(15.0 -5.143516556418883e-14 137.5) '(14.772116295183102 2.604722665004059 137.77777777777777) "")
 (command "line" '(14.772116295183102 2.604722665004059 137.77777777777777) '(14.095389311788681 5.130302149884876 138.05555555555554) "")
 (command "line" '(14.095389311788681 5.130302149884876 138.05555555555554) '(12.990381056766584 7.499999999999993 138.33333333333334) "")
 (command "line" '(12.990381056766584 7.499999999999993 138.33333333333334) '(11.490666646784712 9.64181414529804 138.61111111111111) "")
 (command "line" '(11.490666646784712 9.64181414529804 138.61111111111111) '(9.641814145298182 11.490666646784593 138.88888888888889) "")
 (command "line" '(9.641814145298182 11.490666646784593 138.88888888888889) '(7.500000000000153 12.990381056766491 139.16666666666666) "")
 (command "line" '(7.500000000000153 12.990381056766491 139.16666666666666) '(5.130302149885049 14.095389311788619 139.44444444444446) "")
 (command "line" '(5.130302149885049 14.095389311788619 139.44444444444446) '(2.60472266500403 14.772116295183107 139.72222222222223) "")
 (command "line" '(2.60472266500403 14.772116295183107 139.72222222222223) '(1.322897084365606e-13 15.0 140.0) "")
 (command "line" '(1.322897084365606e-13 15.0 140.0) '(-2.6047226650039796 14.772116295183118 140.27777777777777) "")
 (command "line" '(-2.6047226650039796 14.772116295183118 140.27777777777777) '(-5.130302149885001 14.095389311788637 140.55555555555554) "")
 (command "line" '(-5.130302149885001 14.095389311788637 140.55555555555554) '(-7.499999999999924 12.990381056766624 140.83333333333334) "")
 (command "line" '(-7.499999999999924 12.990381056766624 140.83333333333334) '(-9.641814145297978 11.490666646784764 141.11111111111111) "")
 (command "line" '(-9.641814145297978 11.490666646784764 141.11111111111111) '(-11.490666646784678 9.641814145298081 141.38888888888889) "")
 (command "line" '(-11.490666646784678 9.641814145298081 141.38888888888889) '(-12.990381056766557 7.500000000000038 141.66666666666666) "")
 (command "line" '(-12.990381056766557 7.500000000000038 141.66666666666666) '(-14.095389311788592 5.130302149885126 141.94444444444446) "")
 (command "line" '(-14.095389311788592 5.130302149885126 141.94444444444446) '(-14.772116295183094 2.6047226650041098 142.22222222222223) "")
 (command "line" '(-14.772116295183094 2.6047226650041098 142.22222222222223) '(-15.0 -1.8569419097650732e-17 142.5) "")
 (command "line" '(-15.0 -1.8569419097650732e-17 142.5) '(-14.77211629518313 -2.6047226650038997 142.77777777777777) "")
 (command "line" '(-14.77211629518313 -2.6047226650038997 142.77777777777777) '(-14.095389311788665 -5.130302149884925 143.05555555555554) "")
 (command "line" '(-14.095389311788665 -5.130302149884925 143.05555555555554) '(-12.990381056766557 -7.500000000000038 143.33333333333334) "")
 (command "line" '(-12.990381056766557 -7.500000000000038 143.33333333333334) '(-11.490666646784678 -9.641814145298081 143.61111111111111) "")
 (command "line" '(-11.490666646784678 -9.641814145298081 143.61111111111111) '(-9.641814145298142 -11.490666646784627 143.88888888888889) "")
 (command "line" '(-9.641814145298142 -11.490666646784627 143.88888888888889) '(-7.500000000000108 -12.990381056766518 144.16666666666666) "")
 (command "line" '(-7.500000000000108 -12.990381056766518 144.16666666666666) '(-5.130302149885001 -14.095389311788637 144.44444444444446) "")
 (command "line" '(-5.130302149885001 -14.095389311788637 144.44444444444446) '(-2.6047226650039796 -14.772116295183118 144.72222222222223) "")
 (command "line" '(-2.6047226650039796 -14.772116295183118 144.72222222222223) '(-8.083597345327414e-14 -15.0 145.0) "")
 (command "line" '(-8.083597345327414e-14 -15.0 145.0) '(2.60472266500403 -14.772116295183107 145.27777777777777) "")
 (command "line" '(2.60472266500403 -14.772116295183107 145.27777777777777) '(5.13030214988505 -14.095389311788619 145.55555555555554) "")
 (command "line" '(5.13030214988505 -14.095389311788619 145.55555555555554) '(7.499999999999968 -12.990381056766598 145.83333333333334) "")
 (command "line" '(7.499999999999968 -12.990381056766598 145.83333333333334) '(9.641814145298019 -11.49066664678473 146.11111111111111) "")
 (command "line" '(9.641814145298019 -11.49066664678473 146.11111111111111) '(11.490666646784712 -9.64181414529804 146.38888888888889) "")
 (command "line" '(11.490666646784712 -9.64181414529804 146.38888888888889) '(12.990381056766477 -7.5000000000001785 146.66666666666666) "")
 (command "line" '(12.990381056766477 -7.5000000000001785 146.66666666666666) '(14.09538931178861 -5.130302149885077 146.94444444444446) "")
 (command "line" '(14.09538931178861 -5.130302149885077 146.94444444444446) '(14.772116295183102 -2.604722665004059 147.22222222222223) "")
 (command "line" '(14.772116295183102 -2.604722665004059 147.22222222222223) '(15.0 -1.6169051632564592e-13 147.5) "")
 (command "line" '(15.0 -1.6169051632564592e-13 147.5) '(14.772116295183121 2.6047226650039503 147.77777777777777) "")
 (command "line" '(14.772116295183121 2.6047226650039503 147.77777777777777) '(14.095389311788647 5.130302149884973 148.05555555555554) "")
 (command "line" '(14.095389311788647 5.130302149884973 148.05555555555554) '(12.990381056766532 7.5000000000000835 148.33333333333334) "")
 (command "line" '(12.990381056766532 7.5000000000000835 148.33333333333334) '(11.490666646784781 9.641814145297957 148.61111111111111) "")
 (command "line" '(11.490666646784781 9.641814145297957 148.61111111111111) '(9.641814145298104 11.49066664678466 148.88888888888889) "")
 (command "line" '(9.641814145298104 11.49066664678466 148.88888888888889) '(7.500000000000063 12.990381056766543 149.16666666666666) "")
 (command "line" '(7.500000000000063 12.990381056766543 149.16666666666666) '(5.1303021498851535 14.095389311788582 149.44444444444446) "")
 (command "line" '(5.1303021498851535 14.095389311788582 149.44444444444446) '(2.6047226650041386 14.772116295183089 149.72222222222223) "")
 (command "line" '(2.6047226650041386 14.772116295183089 149.72222222222223) '(2.938223846998765e-14 15.0 150.0) "")
 (command "line" '(2.938223846998765e-14 15.0 150.0) '(-2.604722665003871 14.772116295183135 150.27777777777777) "")
 (command "line" '(-2.604722665003871 14.772116295183135 150.27777777777777) '(-5.130302149884898 14.095389311788674 150.55555555555554) "")
 (command "line" '(-5.130302149884898 14.095389311788674 150.55555555555554) '(-7.500000000000013 12.990381056766573 150.83333333333334) "")
 (command "line" '(-7.500000000000013 12.990381056766573 150.83333333333334) '(-9.641814145298058 11.490666646784696 151.11111111111111) "")
 (command "line" '(-9.641814145298058 11.490666646784696 151.11111111111111) '(-11.490666646784607 9.641814145298165 151.38888888888889) "")
 (command "line" '(-11.490666646784607 9.641814145298165 151.38888888888889) '(-12.990381056766502 7.500000000000133 151.66666666666666) "")
 (command "line" '(-12.990381056766502 7.500000000000133 151.66666666666666) '(-14.095389311788626 5.130302149885029 151.94444444444446) "")
 (command "line" '(-14.095389311788626 5.130302149885029 151.94444444444446) '(-14.772116295183112 2.604722665004008 152.22222222222223) "")
 (command "line" '(-14.772116295183112 2.604722665004008 152.22222222222223) '(-15.0 1.1023678134235943e-13 152.5) "")
 (command "line" '(-15.0 1.1023678134235943e-13 152.5) '(-14.772116295183112 -2.604722665004001 152.77777777777777) "")
 (command "line" '(-14.772116295183112 -2.604722665004001 152.77777777777777) '(-14.09538931178863 -5.130302149885021 153.05555555555554) "")
 (command "line" '(-14.09538931178863 -5.130302149885021 153.05555555555554) '(-12.990381056766612 -7.499999999999942 153.33333333333334) "")
 (command "line" '(-12.990381056766612 -7.499999999999942 153.33333333333334) '(-11.49066664678475 -9.641814145297996 153.61111111111111) "")
 (command "line" '(-11.49066664678475 -9.641814145297996 153.61111111111111) '(-9.641814145298063 -11.490666646784693 153.88888888888889) "")
 (command "line" '(-9.641814145298063 -11.490666646784693 153.88888888888889) '(-7.500000000000019 -12.99038105676657 154.16666666666666) "")
 (command "line" '(-7.500000000000019 -12.99038105676657 154.16666666666666) '(-5.130302149885105 -14.0953893117886 154.44444444444446) "")
 (command "line" '(-5.130302149885105 -14.0953893117886 154.44444444444446) '(-2.604722665004088 -14.772116295183096 154.72222222222223) "")
 (command "line" '(-2.604722665004088 -14.772116295183096 154.72222222222223) '(2.2071496513298835e-14 -15.0 155.0) "")
 (command "line" '(2.2071496513298835e-14 -15.0 155.0) '(2.6047226650039215 -14.772116295183126 155.27777777777777) "")
 (command "line" '(2.6047226650039215 -14.772116295183126 155.27777777777777) '(5.130302149884946 -14.095389311788656 155.55555555555554) "")
 (command "line" '(5.130302149884946 -14.095389311788656 155.55555555555554) '(7.500000000000057 -12.990381056766548 155.83333333333334) "")
 (command "line" '(7.500000000000057 -12.990381056766548 155.83333333333334) '(9.641814145298097 -11.490666646784664 156.11111111111111) "")
 (command "line" '(9.641814145298097 -11.490666646784664 156.11111111111111) '(11.490666646784641 -9.641814145298126 156.38888888888889) "")
 (command "line" '(11.490666646784641 -9.641814145298126 156.38888888888889) '(12.990381056766529 -7.500000000000088 156.66666666666666) "")
 (command "line" '(12.990381056766529 -7.500000000000088 156.66666666666666) '(14.095389311788646 -5.13030214988498 156.94444444444446) "")
 (command "line" '(14.095389311788646 -5.13030214988498 156.94444444444446) '(14.772116295183084 -2.604722665004168 157.22222222222223) "")
 (command "line" '(14.772116295183084 -2.604722665004168 157.22222222222223) '(15.0 -5.878304635907296e-14 157.5) "")
 (command "line" '(15.0 -5.878304635907296e-14 157.5) '(14.772116295183103 2.604722665004052 157.77777777777777) "")
 (command "line" '(14.772116295183103 2.604722665004052 157.77777777777777) '(14.095389311788612 5.13030214988507 158.05555555555554) "")
 (command "line" '(14.095389311788612 5.13030214988507 158.05555555555554) '(12.990381056766694 7.499999999999803 158.33333333333334) "")
 (command "line" '(12.990381056766694 7.499999999999803 158.33333333333334) '(11.490666646784717 9.641814145298035 158.61111111111111) "")
 (command "line" '(11.490666646784717 9.641814145298035 158.61111111111111) '(9.641814145298188 11.49066664678459 158.88888888888889) "")
 (command "line" '(9.641814145298188 11.49066664678459 158.88888888888889) '(7.499999999999974 12.990381056766594 159.16666666666666) "")
 (command "line" '(7.499999999999974 12.990381056766594 159.16666666666666) '(5.130302149885257 14.095389311788542 159.44444444444446) "")
 (command "line" '(5.130302149885257 14.095389311788542 159.44444444444446) '(2.6047226650040374 14.772116295183107 159.72222222222223) "")
 (command "line" '(2.6047226650040374 14.772116295183107 159.72222222222223) '(1.3963758923144472e-13 15.0 160.0) "")
 (command "line" '(1.3963758923144472e-13 15.0 160.0) '(-2.604722665003972 14.77211629518312 160.27777777777777) "")
 (command "line" '(-2.604722665003972 14.77211629518312 160.27777777777777) '(-5.130302149885194 14.095389311788566 160.55555555555557) "")
 (command "line" '(-5.130302149885194 14.095389311788566 160.55555555555557) '(-7.499999999999917 12.990381056766628 160.83333333333331) "")
 (command "line" '(-7.499999999999917 12.990381056766628 160.83333333333331) '(-9.641814145297975 11.490666646784769 161.11111111111111) "")
 (command "line" '(-9.641814145297975 11.490666646784769 161.11111111111111) '(-11.490666646784673 9.641814145298085 161.38888888888889) "")
 (command "line" '(-11.490666646784673 9.641814145298085 161.38888888888889) '(-12.990381056766553 7.500000000000045 161.66666666666669) "")
 (command "line" '(-12.990381056766553 7.500000000000045 161.66666666666669) '(-14.095389311788589 5.130302149885132 161.94444444444443) "")
 (command "line" '(-14.095389311788589 5.130302149885132 161.94444444444443) '(-14.772116295183093 2.604722665004117 162.22222222222223) "")
 (command "line" '(-14.772116295183093 2.604722665004117 162.22222222222223) '(-15.0 7.329311375786468e-15 162.5) "")
 (command "line" '(-15.0 7.329311375786468e-15 162.5) '(-14.772116295183132 -2.6047226650038926 162.77777777777777) "")
 (command "line" '(-14.772116295183132 -2.6047226650038926 162.77777777777777) '(-14.095389311788594 -5.130302149885118 163.05555555555557) "")
 (command "line" '(-14.095389311788594 -5.130302149885118 163.05555555555557) '(-12.990381056766667 -7.499999999999847 163.33333333333331) "")
 (command "line" '(-12.990381056766667 -7.499999999999847 163.33333333333331) '(-11.490666646784684 -9.641814145298076 163.61111111111111) "")
 (command "line" '(-11.490666646784684 -9.641814145298076 163.61111111111111) '(-9.641814145298149 -11.490666646784621 163.88888888888889) "")
 (command "line" '(-9.641814145298149 -11.490666646784621 163.88888888888889) '(-7.49999999999993 -12.990381056766621 164.16666666666669) "")
 (command "line" '(-7.49999999999993 -12.990381056766621 164.16666666666669) '(-5.130302149885208 -14.095389311788562 164.44444444444443) "")
 (command "line" '(-5.130302149885208 -14.095389311788562 164.44444444444443) '(-2.6047226650039867 -14.772116295183116 164.72222222222223) "")
 (command "line" '(-2.6047226650039867 -14.772116295183116 164.72222222222223) '(-8.818385424815826e-14 -15.0 165.0) "")
 (command "line" '(-8.818385424815826e-14 -15.0 165.0) '(2.6047226650040227 -14.772116295183109 165.27777777777777) "")
 (command "line" '(2.6047226650040227 -14.772116295183109 165.27777777777777) '(5.1303021498850425 -14.09538931178862 165.55555555555557) "")
 (command "line" '(5.1303021498850425 -14.09538931178862 165.55555555555557) '(7.499999999999777 -12.990381056766708 165.83333333333331) "")
 (command "line" '(7.499999999999777 -12.990381056766708 165.83333333333331) '(9.641814145298012 -11.490666646784735 166.11111111111111) "")
 (command "line" '(9.641814145298012 -11.490666646784735 166.11111111111111) '(11.490666646784707 -9.641814145298047 166.38888888888889) "")
 (command "line" '(11.490666646784707 -9.641814145298047 166.38888888888889) '(12.990381056766578 -7.5 166.66666666666669) "")
 (command "line" '(12.990381056766578 -7.5 166.66666666666669) '(14.095389311788534 -5.130302149885285 166.94444444444443) "")
 (command "line" '(14.095389311788534 -5.130302149885285 166.94444444444443) '(14.772116295183102 -2.6047226650040662 167.22222222222223) "")
 (command "line" '(14.772116295183102 -2.6047226650040662 167.22222222222223) '(15.0 4.4124423607500014e-14 167.5) "")
 (command "line" '(15.0 4.4124423607500014e-14 167.5) '(14.772116295183123 2.6047226650039432 167.77777777777777) "")
 (command "line" '(14.772116295183123 2.6047226650039432 167.77777777777777) '(14.095389311788576 5.130302149885167 168.05555555555557) "")
 (command "line" '(14.095389311788576 5.130302149885167 168.05555555555557) '(12.990381056766642 7.499999999999892 168.33333333333331) "")
 (command "line" '(12.990381056766642 7.499999999999892 168.33333333333331) '(11.490666646784787 9.64181414529795 168.61111111111111) "")
 (command "line" '(11.490666646784787 9.64181414529795 168.61111111111111) '(9.64181414529811 11.490666646784655 168.88888888888889) "")
 (command "line" '(9.64181414529811 11.490666646784655 168.88888888888889) '(7.499999999999885 12.990381056766646 169.16666666666669) "")
 (command "line" '(7.499999999999885 12.990381056766646 169.16666666666669) '(5.13030214988516 14.095389311788578 169.44444444444443) "")
 (command "line" '(5.13030214988516 14.095389311788578 169.44444444444443) '(2.6047226650041457 14.772116295183087 169.72222222222223) "")
 (command "line" '(2.6047226650041457 14.772116295183087 169.72222222222223) '(3.673011926487177e-14 15.0 170.0) "")
 (command "line" '(3.673011926487177e-14 15.0 170.0) '(-2.6047226650038633 14.772116295183137 170.27777777777777) "")
 (command "line" '(-2.6047226650038633 14.772116295183137 170.27777777777777) '(-5.1303021498850905 14.095389311788605 170.55555555555557) "")
 (command "line" '(-5.1303021498850905 14.095389311788605 170.55555555555557) '(-7.4999999999998215 12.990381056766683 170.83333333333331) "")
 (command "line" '(-7.4999999999998215 12.990381056766683 170.83333333333331) '(-9.641814145298053 11.490666646784701 171.11111111111111) "")
 (command "line" '(-9.641814145298053 11.490666646784701 171.11111111111111) '(-11.490666646784602 9.64181414529817 171.38888888888889) "")
 (command "line" '(-11.490666646784602 9.64181414529817 171.38888888888889) '(-12.990381056766605 7.499999999999955 171.66666666666669) "")
 (command "line" '(-12.990381056766605 7.499999999999955 171.66666666666669) '(-14.095389311788551 5.130302149885235 171.94444444444443) "")
 (command "line" '(-14.095389311788551 5.130302149885235 171.94444444444443) '(-14.77211629518311 2.604722665004015 172.22222222222223) "")
 (command "line" '(-14.77211629518311 2.604722665004015 172.22222222222223) '(-15.0 1.1758466213724357e-13 172.5) "")
 (command "line" '(-15.0 1.1758466213724357e-13 172.5) '(-14.772116295183114 -2.604722665003994 172.77777777777777) "")
 (command "line" '(-14.772116295183114 -2.604722665003994 172.77777777777777) '(-14.095389311788631 -5.130302149885015 173.05555555555557) "")
 (command "line" '(-14.095389311788631 -5.130302149885015 173.05555555555557) '(-12.990381056766616 -7.499999999999936 173.33333333333331) "")
 (command "line" '(-12.990381056766616 -7.499999999999936 173.33333333333331) '(-11.490666646784753 -9.64181414529799 173.61111111111111) "")
 (command "line" '(-11.490666646784753 -9.64181414529799 173.61111111111111) '(-9.641814145298069 -11.490666646784689 173.88888888888889) "")
 (command "line" '(-9.641814145298069 -11.490666646784689 173.88888888888889) '(-7.500000000000025 -12.990381056766566 174.16666666666669) "")
 (command "line" '(-7.500000000000025 -12.990381056766566 174.16666666666669) '(-5.1303021498853125 -14.095389311788523 174.44444444444443) "")
 (command "line" '(-5.1303021498853125 -14.095389311788523 174.44444444444443) '(-2.604722665004095 -14.772116295183096 174.72222222222223) "")
 (command "line" '(-2.604722665004095 -14.772116295183096 174.72222222222223) '(1.4723615718414713e-14 -15.0 175.0) "")
 (command "line" '(1.4723615718414713e-14 -15.0 175.0) '(2.6047226650039144 -14.772116295183128 175.27777777777777) "")
 (command "line" '(2.6047226650039144 -14.772116295183128 175.27777777777777) '(5.130302149885139 -14.095389311788587 175.55555555555557) "")
 (command "line" '(5.130302149885139 -14.095389311788587 175.55555555555557) '(7.499999999999866 -12.990381056766656 175.83333333333331) "")
 (command "line" '(7.499999999999866 -12.990381056766656 175.83333333333331) '(9.641814145298092 -11.490666646784668 176.11111111111111) "")
 (command "line" '(9.641814145298092 -11.490666646784668 176.11111111111111) '(11.490666646784636 -9.641814145298133 176.38888888888889) "")
 (command "line" '(11.490666646784636 -9.641814145298133 176.38888888888889) '(12.99038105676663 -7.499999999999911 176.66666666666669) "")
 (command "line" '(12.99038105676663 -7.499999999999911 176.66666666666669) '(14.095389311788567 -5.130302149885187 176.94444444444443) "")
 (command "line" '(14.095389311788567 -5.130302149885187 176.94444444444443) '(14.772116295183082 -2.6047226650041746 177.22222222222223) "")
 (command "line" '(14.772116295183082 -2.6047226650041746 177.22222222222223) '(15.0 -6.613092715395708e-14 177.5) "")
 (command "line" '(15.0 -6.613092715395708e-14 177.5) '(14.772116295183105 2.6047226650040445 177.77777777777777) "")
 (command "line" '(14.772116295183105 2.6047226650040445 177.77777777777777) '(14.095389311788615 5.130302149885063 178.05555555555557) "")
 (command "line" '(14.095389311788615 5.130302149885063 178.05555555555557) '(12.990381056766697 7.499999999999796 178.33333333333331) "")
 (command "line" '(12.990381056766697 7.499999999999796 178.33333333333331) '(11.490666646784721 9.64181414529803 178.61111111111111) "")
 (command "line" '(11.490666646784721 9.64181414529803 178.61111111111111) '(9.641814145298193 11.490666646784584 178.88888888888889) "")
 (command "line" '(9.641814145298193 11.490666646784584 178.88888888888889) '(7.4999999999999805 12.99038105676659 179.16666666666669) "")
 (command "line" '(7.4999999999999805 12.99038105676659 179.16666666666669) '(5.130302149885264 14.09538931178854 179.44444444444443) "")
 (command "line" '(5.130302149885264 14.09538931178854 179.44444444444443) '(2.6047226650040445 14.772116295183105 179.72222222222223) "")
 (command "line" '(2.6047226650040445 14.772116295183105 179.72222222222223) '(1.4698547002632885e-13 15.0 180.0) "")
 (command "line" '(1.4698547002632885e-13 15.0 180.0) '(-2.604722665003965 14.77211629518312 180.27777777777777) "")
 (command "line" '(-2.604722665003965 14.77211629518312 180.27777777777777) '(-5.130302149885187 14.095389311788567 180.55555555555557) "")
 (command "line" '(-5.130302149885187 14.095389311788567 180.55555555555557) '(-7.499999999999911 12.99038105676663 180.83333333333331) "")
 (command "line" '(-7.499999999999911 12.99038105676663 180.83333333333331) '(-9.641814145297968 11.490666646784774 181.11111111111111) "")
 (command "line" '(-9.641814145297968 11.490666646784774 181.11111111111111) '(-11.490666646784668 9.641814145298092 181.38888888888889) "")
 (command "line" '(-11.490666646784668 9.641814145298092 181.38888888888889) '(-12.99038105676655 7.5000000000000515 181.66666666666669) "")
 (command "line" '(-12.99038105676655 7.5000000000000515 181.66666666666669) '(-14.095389311788587 5.130302149885139 181.94444444444443) "")
 (command "line" '(-14.095389311788587 5.130302149885139 181.94444444444443) '(-14.77211629518309 2.604722665004124 182.22222222222223) "")
 (command "line" '(-14.77211629518309 2.604722665004124 182.22222222222223) '(-15.0 1.4677192170670588e-14 182.5) "")
 (command "line" '(-15.0 1.4677192170670588e-14 182.5) '(-14.772116295183134 -2.6047226650038855 182.77777777777777) "")
 (command "line" '(-14.772116295183134 -2.6047226650038855 182.77777777777777) '(-14.095389311788596 -5.130302149885112 183.05555555555557) "")
 (command "line" '(-14.095389311788596 -5.130302149885112 183.05555555555557) '(-12.990381056766672 -7.499999999999841 183.33333333333331) "")
 (command "line" '(-12.990381056766672 -7.499999999999841 183.33333333333331) '(-11.490666646784689 -9.641814145298069 183.61111111111111) "")
 (command "line" '(-11.490666646784689 -9.641814145298069 183.61111111111111) '(-9.641814145298154 -11.490666646784616 183.88888888888889) "")
 (command "line" '(-9.641814145298154 -11.490666646784616 183.88888888888889) '(-7.499999999999936 -12.990381056766616 184.16666666666669) "")
 (command "line" '(-7.499999999999936 -12.990381056766616 184.16666666666669) '(-5.130302149885216 -14.095389311788558 184.44444444444443) "")
 (command "line" '(-5.130302149885216 -14.095389311788558 184.44444444444443) '(-2.604722665003994 -14.772116295183114 184.72222222222223) "")
 (command "line" '(-2.604722665003994 -14.772116295183114 184.72222222222223) '(-9.553173504304237e-14 -15.0 185.0) "")
 (command "line" '(-9.553173504304237e-14 -15.0 185.0) '(2.6047226650040156 -14.77211629518311 185.27777777777777) "")
 (command "line" '(2.6047226650040156 -14.77211629518311 185.27777777777777) '(5.130302149885035 -14.095389311788624 185.55555555555557) "")
 (command "line" '(5.130302149885035 -14.095389311788624 185.55555555555557) '(7.499999999999771 -12.990381056766712 185.83333333333331) "")
 (command "line" '(7.499999999999771 -12.990381056766712 185.83333333333331) '(9.641814145298007 -11.49066664678474 186.11111111111111) "")
 (command "line" '(9.641814145298007 -11.49066664678474 186.11111111111111) '(11.490666646784701 -9.641814145298053 186.38888888888889) "")
 (command "line" '(11.490666646784701 -9.641814145298053 186.38888888888889) '(12.990381056766577 -7.500000000000007 186.66666666666669) "")
 (command "line" '(12.990381056766577 -7.500000000000007 186.66666666666669) '(14.095389311788532 -5.130302149885291 186.94444444444443) "")
 (command "line" '(14.095389311788532 -5.130302149885291 186.94444444444443) '(14.7721162951831 -2.604722665004074 187.22222222222223) "")
 (command "line" '(14.7721162951831 -2.604722665004074 187.22222222222223) '(15.0 -1.7638627791541416e-13 187.5) "")
 (command "line" '(15.0 -1.7638627791541416e-13 187.5) '(14.772116295183123 2.6047226650039357 187.77777777777777) "")
 (command "line" '(14.772116295183123 2.6047226650039357 187.77777777777777) '(14.095389311788578 5.13030214988516 188.05555555555557) "")
 (command "line" '(14.095389311788578 5.13030214988516 188.05555555555557) '(12.990381056766646 7.499999999999885 188.33333333333331) "")
 (command "line" '(12.990381056766646 7.499999999999885 188.33333333333331) '(11.490666646784792 9.641814145297946 188.61111111111111) "")
 (command "line" '(11.490666646784792 9.641814145297946 188.61111111111111) '(9.641814145298113 11.49066664678465 188.88888888888889) "")
 (command "line" '(9.641814145298113 11.49066664678465 188.88888888888889) '(7.499999999999892 12.990381056766642 189.16666666666669) "")
 (command "line" '(7.499999999999892 12.990381056766642 189.16666666666669) '(5.130302149885166 14.095389311788576 189.44444444444443) "")
 (command "line" '(5.130302149885166 14.095389311788576 189.44444444444443) '(2.6047226650041533 14.772116295183086 189.72222222222223) "")
 (command "line" '(2.6047226650041533 14.772116295183086 189.72222222222223) '(4.407800005975589e-14 15.0 190.0) "")
 (command "line" '(4.407800005975589e-14 15.0 190.0) '(-2.604722665003856 14.772116295183139 190.27777777777777) "")
 (command "line" '(-2.604722665003856 14.772116295183139 190.27777777777777) '(-5.130302149885084 14.095389311788606 190.55555555555557) "")
 (command "line" '(-5.130302149885084 14.095389311788606 190.55555555555557) '(-7.499999999999815 12.990381056766685 190.83333333333331) "")
 (command "line" '(-7.499999999999815 12.990381056766685 190.83333333333331) '(-9.641814145298047 11.490666646784707 191.11111111111111) "")
 (command "line" '(-9.641814145298047 11.490666646784707 191.11111111111111) '(-11.490666646784598 9.641814145298175 191.38888888888889) "")
 (command "line" '(-11.490666646784598 9.641814145298175 191.38888888888889) '(-12.990381056766601 7.499999999999962 191.66666666666669) "")
 (command "line" '(-12.990381056766601 7.499999999999962 191.66666666666669) '(-14.095389311788548 5.130302149885243 191.94444444444443) "")
 (command "line" '(-14.095389311788548 5.130302149885243 191.94444444444443) '(-14.772116295183109 2.6047226650040227 192.22222222222223) "")
 (command "line" '(-14.772116295183109 2.6047226650040227 192.22222222222223) '(-15.0 1.2493254293212768e-13 192.5) "")
 (command "line" '(-15.0 1.2493254293212768e-13 192.5) '(-14.772116295183116 -2.6047226650039867 192.77777777777777) "")
 (command "line" '(-14.772116295183116 -2.6047226650039867 192.77777777777777) '(-14.095389311788635 -5.130302149885008 193.05555555555557) "")
 (command "line" '(-14.095389311788635 -5.130302149885008 193.05555555555557) '(-12.990381056766621 -7.49999999999993 193.33333333333331) "")
 (command "line" '(-12.990381056766621 -7.49999999999993 193.33333333333331) '(-11.490666646784758 -9.641814145297985 193.61111111111111) "")
 (command "line" '(-11.490666646784758 -9.641814145297985 193.61111111111111) '(-9.641814145298076 -11.490666646784684 193.88888888888889) "")
 (command "line" '(-9.641814145298076 -11.490666646784684 193.88888888888889) '(-7.500000000000032 -12.99038105676656 194.16666666666669) "")
 (command "line" '(-7.500000000000032 -12.99038105676656 194.16666666666669) '(-5.130302149885319 -14.095389311788521 194.44444444444443) "")
 (command "line" '(-5.130302149885319 -14.095389311788521 194.44444444444443) '(-2.604722665004102 -14.772116295183096 194.72222222222223) "")
 (command "line" '(-2.604722665004102 -14.772116295183096 194.72222222222223) '(7.375734923530595e-15 -15.0 195.0) "")
 (command "line" '(7.375734923530595e-15 -15.0 195.0) '(2.6047226650039073 -14.772116295183128 195.27777777777777) "")
 (command "line" '(2.6047226650039073 -14.772116295183128 195.27777777777777) '(5.130302149885132 -14.095389311788589 195.55555555555557) "")
 (command "line" '(5.130302149885132 -14.095389311788589 195.55555555555557) '(7.49999999999986 -12.99038105676666 195.83333333333331) "")
 (command "line" '(7.49999999999986 -12.99038105676666 195.83333333333331) '(9.641814145298085 -11.490666646784673 196.11111111111111) "")
 (command "line" '(9.641814145298085 -11.490666646784673 196.11111111111111) '(11.490666646784632 -9.641814145298136 196.38888888888889) "")
 (command "line" '(11.490666646784632 -9.641814145298136 196.38888888888889) '(12.990381056766628 -7.4999999999999165 196.66666666666669) "")
 (command "line" '(12.990381056766628 -7.4999999999999165 196.66666666666669) '(14.095389311788566 -5.130302149885194 196.94444444444443) "")
 (command "line" '(14.095389311788566 -5.130302149885194 196.94444444444443) '(14.77211629518308 -2.6047226650041817 197.22222222222223) "")
 (command "line" '(14.77211629518308 -2.6047226650041817 197.22222222222223) '(15.0 -7.347880794884119e-14 197.5) "")
 (command "line" '(15.0 -7.347880794884119e-14 197.5) '(14.772116295183107 2.6047226650040374 197.77777777777777) "")
 (command "line" '(14.772116295183107 2.6047226650040374 197.77777777777777) '(14.095389311788617 5.130302149885057 198.05555555555557) "")
 (command "line" '(14.095389311788617 5.130302149885057 198.05555555555557) '(12.9903810567667 7.49999999999979 198.33333333333331) "")
 (command "line" '(12.9903810567667 7.49999999999979 198.33333333333331) '(11.490666646784724 9.641814145298024 198.61111111111111) "")
 (command "line" '(11.490666646784724 9.641814145298024 198.61111111111111) '(9.641814145298198 11.490666646784579 198.88888888888889) "")
 (command "line" '(9.641814145298198 11.490666646784579 198.88888888888889) '(7.499999999999988 12.990381056766587 199.16666666666669) "")
 (command "line" '(7.499999999999988 12.990381056766587 199.16666666666669) '(5.130302149885271 14.095389311788539 199.44444444444443) "")
 (command "line" '(5.130302149885271 14.095389311788539 199.44444444444443) '(2.6047226650040516 14.772116295183103 199.72222222222223) "")
 (command "line" '(2.6047226650040516 14.772116295183103 199.72222222222223) '(1.5433335082121296e-13 15.0 200.0) "")
