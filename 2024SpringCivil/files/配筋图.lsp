(command "line" '(0 0) '(30 0) "")
 (command "line" '(30 0) '(30 60) "")
 (command "line" '(30 60) '(0 60) "")
 (command "line" '(0 60) '(0 0) "")
  (command "donut" 0 4 '(5.0 5.0) "") 
  (command "donut" 0 4 '(11.666666666666668 5.0) "") 
  (command "donut" 0 4 '(18.333333333333336 5.0) "") 
  (command "donut" 0 4 '(25.0 5.0) "") 
  (command "donut" 0 4 '(4.0 56.0) "") 
  (command "donut" 0 4 '(26.0 56.0) "")
